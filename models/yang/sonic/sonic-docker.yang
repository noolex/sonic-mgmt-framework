module sonic-docker {
    namespace "http://github.com/Azure/sonic-docker";
    prefix sdocker;
    yang-version 1.1;

    organization
        "SONiC";

    contact
        "SONiC";

    description
        "SONiC Docker Management";

    revision 2020-04-08 {
        description
            "Initial revision.";
    }

    rpc docker-exec {
        description "Run command in container";
        input  {
            leaf container-name {
                type string;
                description "Container name";
            }
            leaf command {
                type string;
                description "Command to run";
            }
        }
        output {
            leaf status {
                type string;
                description
                    "Success / failure in running command";
            }
            leaf code {
                type int32;
            }
        }
    }
}
