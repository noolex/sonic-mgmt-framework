module sonic-ifa {
    namespace "http://github.com/Azure/sonic-ifa";
    prefix ifa;

    import sonic-extension {
            prefix sonic-ext;
    }

    organization
        "SONiC";

    contact
        "SONiC";

    description
        "SONIC TAM IFA";

    revision 2019-11-12 {
        description
            "Initial revision.";
    }

    container sonic-ifa {

        container TAM_INT_IFA_FEATURE_TABLE {

            list TAM_INT_IFA_FEATURE_TABLE_LIST {
                key "name";
	        sonic-ext:custom-validation ValidateTAMFeature;

                leaf name {
                    type enumeration {
                        enum feature;
                    }
                    description
                        "Feature identifier name in IFA feature table.";
                }

                leaf enable {
                    type boolean;
                    description
                        "Flag to enable or disable IFA feature.";
                }
            }
        }

        container TAM_INT_IFA_FLOW_TABLE {

            list TAM_INT_IFA_FLOW_TABLE_LIST {
                key "name";
	        sonic-ext:custom-validation ValidateTAMFeature;

                leaf name {
                    type string {
                        pattern '[a-zA-Z0-9]{1}([-a-zA-Z0-9_]{0,32})';
                        length 1..32;
                    }
                    description
                        "Flow name in IFA flow configuration list.";
                }

                leaf acl-table-name {
                    mandatory true;
                    type string;
                    description
                        "ACL table name used in IFA flow configuration table.";
                }

                leaf acl-rule-name {
                    mandatory true;
                    type string;
                    description
                        "ACL rule name used in IFA flow configuration table.";
                }

                leaf sampling-rate {
                    type uint16 {
                        range "1..10000"{
                            error-app-tag "Invalid IFA flow sampling rate.";
                        }
                    }
                    description
                        "Sampling rate for the packets belonging to the flow that
                         need to be tagged with IFA meta-data";
                }

                leaf collector-name {
                    type string {
                        pattern '[a-zA-Z0-9]{1}([-a-zA-Z0-9_]{0,32})';
                        length 1..32;
                    }
                    description
                        "Collector name where IFA report is to be forwarded.";
                }
            }
        }
    }
}
