module sonic-flow-based-services {
    namespace "http://github.com/Azure/sonic-flow-based-services";
    prefix sfbs;
    yang-version 1.1;

    import ietf-inet-types {
        prefix inet;
    }

    import sonic-common {
        prefix cmn;
    }

    import sonic-extension {
        prefix sonic-ext;
    }

    import sonic-acl {
        prefix sacl;
    }

    import sonic-port {
        prefix sprt;
    }

    import sonic-portchannel {
        prefix spc;
    }

    import sonic-vlan {
        prefix svlan;
    }

    import sonic-mirror-session {
        prefix sms;
    }

    organization
        "SONiC";

    contact
        "SONiC";

    description
        "SONIC Flow Based Services";

    revision 2020-02-26 {
        description
            "Initial revision.";
    }

    container sonic-flow-based-services {
        container POLICY_TABLE {
            list POLICY_TABLE_LIST {
                key "POLICY_NAME";
                max-elements 256;

                leaf POLICY_NAME {
                    type string {
                        pattern '[a-zA-Z0-9]{1}([-a-zA-Z0-9_]{0,62})';
                        length 1..63;
                    }
                }

                leaf DESCRIPTION {
                    type string {
                        length 1..255 {
                            error-app-tag policy-description-invalid-length;
                        }
                    }
                }

                leaf TYPE {
                    mandatory true;
                    sonic-ext:custom-validation ValidateLeafConstant;
                    type enumeration {
                        enum QOS;
                        enum MONITORING;
                        enum FORWARDING;
                    }
                }
            }
        }

        container CLASSIFIER_TABLE {
            list CLASSIFIER_TABLE_LIST {
                key "CLASSIFIER_NAME";
                max-elements 256;

                leaf CLASSIFIER_NAME {
                    type string {
                        pattern '[a-zA-Z0-9]{1}([-a-zA-Z0-9_]{0,62})';
                        length 1..63;
                    }

                    must "current() != 'default'" {
                        error-app-tag name-not-allowed;
                        error-message "'default' name is not allowed";
                    }
                }

                leaf DESCRIPTION {
                    type string {
                        length 1..255 {
                            error-app-tag policy-description-invalid-length;
                        }
                    }
                }

                leaf MATCH_TYPE {
                    mandatory true;
                    sonic-ext:custom-validation ValidateLeafConstant;
                    type enumeration {
                        enum FIELDS;
                        enum ACL;
                    }
                }

                leaf ACL_NAME {
                    sonic-ext:custom-validation ValidateLeafConstant;
                    when "current()/../MATCH_TYPE = 'ACL'";
                    type leafref {
                        path "/sacl:sonic-acl/sacl:ACL_TABLE/sacl:ACL_TABLE_LIST/sacl:aclname";
                    }
                }

                leaf ETHER_TYPE {
                    when "current()/../MATCH_TYPE = 'FIELDS'";
                    type string {
                        pattern "0[xX][6-9a-fA-F][0-9a-fA-F]{2,3}|0[xX][1-9a-fA-F][0-9a-fA-F]{3,4}" {
                            error-message "Invalid Ether Type";
                            error-app-tag ether-type-invalid;
                        }
                    }
                }

                leaf SRC_MAC {
                    when "current()/../MATCH_TYPE = 'FIELDS'";
                    type string {
                        pattern "[0-9a-fA-F]{2}(:[0-9a-fA-F]{2}){5}|[0-9a-fA-F]{2}(:[0-9a-fA-F]{2}){5}/[0-9a-fA-F]{2}(:[0-9a-fA-F]{2}){5}";
                    }
                }

                leaf DST_MAC {
                    when "current()/../MATCH_TYPE = 'FIELDS'";
                    type string {
                        pattern "[0-9a-fA-F]{2}(:[0-9a-fA-F]{2}){5}|[0-9a-fA-F]{2}(:[0-9a-fA-F]{2}){5}/[0-9a-fA-F]{2}(:[0-9a-fA-F]{2}){5}";
                    }
                }

                leaf VLAN {
                    when "current()/../MATCH_TYPE = 'FIELDS'";
                    type uint16 {
                        range "1..4094" {
                            error-app-tag vlanid-invalid;
                            error-message "Vlan ID out of range";
                        }
                    }
                }

                leaf PCP {
                    when "current()/../MATCH_TYPE = 'FIELDS'";
                    type uint8 {
                        range "0..7" {
                            error-app-tag invalid-pcp-value;
                            error-message "Invalid PCP Value.";
                        }
                    }
                }

                leaf DEI {
                    when "current()/../MATCH_TYPE = 'FIELDS'";
                    type uint8 {
                        range "0..1" {
                            error-app-tag invalid-dei-value;
                            error-message "Invalid DEI Value.";
                        }
                    }
                }

                leaf IP_PROTOCOL {
                    when "current()/../MATCH_TYPE = 'FIELDS'";
                    must "((translate(current()/../ETHER_TYPE, 'ABCDEFX', 'abcdefx') = '0x800') or ((translate(current()/../ETHER_TYPE, 'ABCDEFX', 'abcdefx') = '0x86dd')) or (not(current()/../ETHER_TYPE)))" {
                        error-app-tag ethertype-not-ipv4-ipv6;
                        error-message "IP Protocol can be configured only when Ethertype is IPv4 or IPv6";
                    }
                    type uint8;
                }

                leaf SRC_IP {
                    when "current()/../MATCH_TYPE = 'FIELDS'";
                    must "(not(current()/../SRC_IPV6)) and (not(current()/../DST_IPV6))" {
                        error-message "Configuring IPv4 and IPv6 header fields in the same classifier is not allowed.";
                    }
                    must "(translate(current()/../ETHER_TYPE, 'ABCDEFX', 'abcdefx') = '0x800') or (not(current()/../ETHER_TYPE))" {
                        error-app-tag src-ip-ethertype-not-ipv4;
                        error-message "Source IP address can be configured only when ethertype is IPv4";
                    }
                    type inet:ipv4-prefix;
                }

                leaf DST_IP {
                    when "current()/../MATCH_TYPE = 'FIELDS'";
                    must "(not(current()/../SRC_IPV6)) and (not(current()/../DST_IPV6))" {
                        error-message "Configuring IPv4 and IPv6 header fields in the same classifier is not allowed.";
                    }
                    must "(translate(current()/../ETHER_TYPE, 'ABCDEFX', 'abcdefx') = '0x800') or (not(current()/../ETHER_TYPE))" {
                        error-app-tag dst-ip-ethertype-not-ipv4;
                        error-message "Destination IP address can be configured only when ethertype is IPv4";
                    }
                    type inet:ipv4-prefix;
                }

                leaf SRC_IPV6 {
                    when "current()/../MATCH_TYPE = 'FIELDS'";
                    must "(not(current()/../SRC_IP)) and (not(current()/../DST_IP))" {
                        error-message "Configuring IPv4 and IPv6 header fields in the same classifier is not allowed.";
                    }
                    must "(translate(current()/../ETHER_TYPE, 'ABCDEFX', 'abcdefx') = '0x86dd') or (not(current()/../ETHER_TYPE))" {
                        error-app-tag src-ip-ethertype-not-ipv6;
                        error-message "Source IPv6 address can be configured only when ethertype is IPv6";
                    }
                    type inet:ipv6-prefix;
                }

                leaf DST_IPV6 {
                    when "current()/../MATCH_TYPE = 'FIELDS'";
                    must "(not(current()/../SRC_IP)) and (not(current()/../DST_IP))" {
                        error-message "Configuring IPv4 and IPv6 header fields in the same classifier is not allowed.";
                    }
                    must "(translate(current()/../ETHER_TYPE, 'ABCDEFX', 'abcdefx') = '0x86dd') or (not(current()/../ETHER_TYPE))" {
                        error-app-tag dst-ip-ethertype-not-ipv6;
                        error-message "Destination IPv6 address can be configured only when ethertype is IPv6";
                    }
                    type inet:ipv6-prefix;
                }

                leaf DSCP {
                    when "current()/../MATCH_TYPE = 'FIELDS'";
                    must "((translate(current()/../ETHER_TYPE, 'ABCDEFX', 'abcdefx') = '0x800') or ((translate(current()/../ETHER_TYPE, 'ABCDEFX', 'abcdefx') = '0x86dd')) or (not(current()/../ETHER_TYPE)))" {
                        error-app-tag ethertype-not-ipv4-ipv6;
                        error-message "IP Protocol can be configured only when Ethertype is IPv4 or IPv6";
                    }
                    type uint8 {
                        range "0..63" {
                            error-app-tag invalid-dscp-value;
                            error-message "Invalid DSCP Value.";
                        }
                    }
                }

                choice src_port {
                    when "current()/MATCH_TYPE = 'FIELDS'";
                    case l4_src_port {
                        leaf L4_SRC_PORT {
                            must "((current()/../IP_PROTOCOL = 6) or (current()/../IP_PROTOCOL = 17))" {
                                error-app-tag ip-protocol-not-tcp-or-udp;
                                error-message "Layer 4 source port can be configured only when IP protocol is TCP or UDP";
                            }
                            must "((translate(current()/../ETHER_TYPE, 'ABCDEFX', 'abcdefx') = '0x800') or ((translate(current()/../ETHER_TYPE, 'ABCDEFX', 'abcdefx') = '0x86dd')) or (not(current()/../ETHER_TYPE)))" {
                                error-app-tag ethertype-not-ipv4-ipv6;
                                error-message "TCP/UDP ports can be configured only when Ethertype is IPv4 or IPv6";
                            }
                            type uint16;
                        }
                    }
                    case l4_src_port_range {
                        leaf L4_SRC_PORT_RANGE {
                            must "((current()/../IP_PROTOCOL = 6) or (current()/../IP_PROTOCOL = 17))" {
                                error-app-tag ip-protocol-not-tcp-or-udp;
                                error-message "Layer 4 source port can be configured only when IP protocol is TCP or UDP";
                            }
                            must "((translate(current()/../ETHER_TYPE, 'ABCDEFX', 'abcdefx') = '0x800') or ((translate(current()/../ETHER_TYPE, 'ABCDEFX', 'abcdefx') = '0x86dd')) or (not(current()/../ETHER_TYPE)))" {
                                error-app-tag ethertype-not-ipv4-ipv6;
                                error-message "TCP/UDP ports can be configured only when Ethertype is IPv4 or IPv6";
                            }
                            type string {
                                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
                            }
                        }
                    }
                }

                choice dst_port {
                    when "current()/MATCH_TYPE = 'FIELDS'";
                    case l4_dst_port {
                        leaf L4_DST_PORT {
                            must "((current()/../IP_PROTOCOL = 6) or (current()/../IP_PROTOCOL = 17))" {
                                error-app-tag ip-protocol-not-tcp-or-udp;
                                error-message "Layer 4 source port can be configured only when IP protocol is TCP or UDP";
                            }
                            must "((translate(current()/../ETHER_TYPE, 'ABCDEFX', 'abcdefx') = '0x800') or ((translate(current()/../ETHER_TYPE, 'ABCDEFX', 'abcdefx') = '0x86dd')) or (not(current()/../ETHER_TYPE)))" {
                                error-app-tag ethertype-not-ipv4-ipv6;
                                error-message "TCP/UDP ports can be configured only when Ethertype is IPv4 or IPv6";
                            }
                            type uint16;
                        }
                    }
                    case l4_dst_port_range {
                        leaf L4_DST_PORT_RANGE {
                            must "((current()/../IP_PROTOCOL = 6) or (current()/../IP_PROTOCOL = 17))" {
                                error-app-tag ip-protocol-not-tcp-or-udp;
                                error-message "Layer 4 source port can be configured only when IP protocol is TCP or UDP";
                            }
                            must "((translate(current()/../ETHER_TYPE, 'ABCDEFX', 'abcdefx') = '0x800') or ((translate(current()/../ETHER_TYPE, 'ABCDEFX', 'abcdefx') = '0x86dd')) or (not(current()/../ETHER_TYPE)))" {
                                error-app-tag ethertype-not-ipv4-ipv6;
                                error-message "TCP/UDP ports can be configured only when Ethertype is IPv4 or IPv6";
                            }
                            type string {
                                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
                            }
                        }
                    }
                }

                leaf TCP_FLAGS {
                    when "current()/../MATCH_TYPE = 'FIELDS'";
                    must "current()/../IP_PROTOCOL = 6" {
                        error-app-tag ip-protocol-not-tcp;
                        error-message "TCP Flags can be configured only when IP protocol is IP protocol is TCP";
                    }

                    type string {
                        pattern "(0[xX][1-9a-fA-F][0-9a-fA-F]?|[1-9][0-9]?|1[0-9]{2}|2[0-5]{2})/(0[xX][1-9a-fA-F][0-9a-fA-F]?|[1-9][0-9]?|1[0-9]{2}|2[0-5]{2})";
                    }
                }
/*
                leaf ICMP_TYPE {
                    when "current()/../MATCH_TYPE = 'FIELDS'";
                    must "((current()/../IP_PROTOCOL = 1) or (current()/../IP_PROTOCOL = 58))" {
                        error-app-tag ip-protocol-not-icmp-or-icmpv6;
                        error-message "ICMP type can be configured only when IP protocol is ICMP or ICMPv6";
                    }
                    type uint8;
                }

                leaf ICMP_CODE {
                    when "current()/../MATCH_TYPE = 'FIELDS'";
                    must "((current()/../IP_PROTOCOL = 1) or (current()/../IP_PROTOCOL = 58))" {
                        error-app-tag ip-protocol-not-icmp-or-icmpv6;
                        error-message "ICMP code can be configured only when IP protocol is ICMP or ICMPv6";
                    }
                    type uint8;
                }
*/
            }
        }

        container POLICY_SECTIONS_TABLE {
            list POLICY_SECTIONS_TABLE_LIST {
                key "POLICY_NAME CLASSIFIER_NAME";
                max-elements 256;

                leaf POLICY_NAME {
                    type leafref {
                        path "/sonic-flow-based-services/POLICY_TABLE/POLICY_TABLE_LIST/POLICY_NAME";
                    }
                }

                leaf CLASSIFIER_NAME {
                    type leafref {
                        path "/sonic-flow-based-services/CLASSIFIER_TABLE/CLASSIFIER_TABLE_LIST/CLASSIFIER_NAME";
                    }
                }

                leaf DESCRIPTION {
                    type string {
                        length 1..255 {
                            error-app-tag policy-description-invalid-length;
                        }
                    }
                }

                leaf PRIORITY {
                    mandatory true;
                    sonic-ext:custom-validation ValidateLeafConstant;
                    type uint16 {
                        range "0..1023" {
                            error-app-tag invalid-priority;
                        }
                    }
                }

                choice flow_actions {
                    /*======================================================================================================
                                                                 QoS Actions
                    ======================================================================================================*/
                    case qos_actions {
                        when "/sonic-flow-based-services/POLICY_TABLE/POLICY_TABLE_LIST[POLICY_NAME=current()/POLICY_NAME]/TYPE = 'QOS'";
                        leaf SET_DSCP {
                            type uint8 {
                                range "0..63" {
                                    error-app-tag invalid-dscp-value;
                                    error-message "Invalid DSCP value.";
                                }
                            }
                        }

                        leaf SET_PCP {
                            type uint8 {
                                range "0..7" {
                                    error-app-tag invalid-pcp-value;
                                    error-message "Invalid PCP value.";
                                }
                            }
                        }
/*
                        leaf SET_TC {
                            type uint8 {
                                range "0..7" {
                                    error-app-tag invalid-traffic-class-value;
                                    error-message "Invalid Traffic Class value.";
                                }
                            }
                        }
*/
                        leaf SET_POLICER_CIR {
                            type uint32 {
                                range "1..4294967295";
                            }
                        }

                        leaf SET_POLICER_CBS {
                            type uint32 {
                                range "1..4294967295";
                            }
                            must "(current()/../SET_POLICER_CIR) and (current()/../SET_POLICER_CIR > 0)" {
                                error-app-tag cir-not-configured;
                                error-message "CBS can't be configured without CIR.";
                            }
                            must "current()*8 >= current()/../SET_POLICER_CIR" {
                                error-app-tag cbs-less-than-cir;
                                error-message "CBS must be greater than or equal to CIR";
                            }
                        }

                        leaf SET_POLICER_PIR {
                            type uint32 {
                                range "1..4294967295";
                            }
                            must "(current()/../SET_POLICER_CIR) and (current()/../SET_POLICER_CIR > 0)" {
                                error-app-tag cir-not-configured;
                                error-message "PIR can't be configured without CIR.";
                            }
                            must "current() >= current()/../SET_POLICER_CIR" {
                                error-app-tag pir-less-than-cir;
                                error-message "PIR must be greater than or equal to CIR";
                            }
                        }

                        leaf SET_POLICER_PBS {
                            type uint32 {
                                range "1..4294967295";
                            }
                            must "(current()/../SET_POLICER_PIR) and (current()/../SET_POLICER_PIR > 0)" {
                                error-app-tag pir-not-configured;
                                error-message "PBS can't be configured without PIR.";
                            }
                            must "current()*8 >= current()/../SET_POLICER_PIR" {
                                error-app-tag pbs-less-than-pir;
                                error-message "PBS must be greater than or equal to PIR";
                            }
                            must "(not(current()/../SET_POLICER_CBS)) or (current() >= current()/../SET_POLICER_CBS)" {
                                error-app-tag pbs-less-than-cbs;
                                error-message "PBS must be greater than or equal to CBS";
                            }
                        }
                    }

                    /*======================================================================================================
                                                               Monitoring Actions
                    ======================================================================================================*/
                    case monitoring_actions {
                        when "/sonic-flow-based-services/POLICY_TABLE/POLICY_TABLE_LIST[POLICY_NAME=current()/POLICY_NAME]/TYPE = 'MONITORING'";
                        leaf SET_MIRROR_SESSION {
                            type leafref {
                                path "/sms:sonic-mirror-session/sms:MIRROR_SESSION/sms:MIRROR_SESSION_LIST/sms:name";
                            }
                        }
                    }

                    /*======================================================================================================
                                                               Forwarding Actions
                    ======================================================================================================*/
                    case forwarding_options {
                        when "/sonic-flow-based-services/POLICY_TABLE/POLICY_TABLE_LIST[POLICY_NAME=current()/POLICY_NAME]/TYPE = 'FORWARDING'";
                        choice egress_options {
                            case l2_egress_option {

                                // <PortName>|<Priority>, <PortName>|<Priority> ....
                                leaf-list SET_INTERFACE {
                                   max-elements 64;
                                   type string {
                                        pattern '((Ethernet([1-3][0-9]{3}|[1-9][0-9]{2}|[1-9][0-9]|[0-9]))|(PortChannel([1-9]|[1-9][0-9]|1[0-9][0-9]|2[0-4][0-9]|25[0-6])))\|'
                                                + '([1-9][0-9]{0,3}|[1-5][0-9]{4}|6[0-4][0-9]{3}|65[0-4][0-9]{2}|655[0-2][0-9]|6553[0-5])?';
                                    }
                                }
                            }
                            case ipv4_egress_option {

                                /* <IPv4Address>|<VRF>|<Priority>,<IPv4Address>|<VRF>|<Priority>.... */
                                leaf-list SET_IP_NEXTHOP {
                                    max-elements 64;
                                    type string {
                                        pattern '((([0-9]|[1-9][0-9]|1[0-9][0-9]|2[0-4][0-9]|25[0-5])\.){3}([0-9]|[1-9][0-9]|1[0-9][0-9]|2[0-4][0-9]|25[0-5]))\|'
                                                + '(default|Vrf[a-zA-Z0-9_-]+)?\|'
                                                + '([1-9][0-9]{0,3}|[1-5][0-9]{4}|6[0-4][0-9]{3}|65[0-4][0-9]{2}|655[0-2][0-9]|6553[0-5])?';
                                    }
                                }
                            }
                            case ipv6_egress_option {

                                /* <IPv6Address>|<VRF>|<Priority>,<IPv6Address>|<VRF>|<Priority>.... */
                                leaf-list SET_IPV6_NEXTHOP {
                                    max-elements 64;
                                    type string {
                                        pattern '(((:|[0-9a-fA-F]{0,4}):)([0-9a-fA-F]{0,4}:){0,5}(([0-9a-fA-F]{0,4}:)?(:|[0-9a-fA-F]{0,4})))\|'
                                                + '(default|Vrf[a-zA-Z0-9_-]+)?\|'
                                                + '([1-9][0-9]{0,3}|[1-5][0-9]{4}|6[0-4][0-9]{3}|65[0-4][0-9]{2}|655[0-2][0-9]|6553[0-5])?';
                                    }
                                }
                            }
                        }

                        leaf DEFAULT_PACKET_ACTION {
                            type enumeration {
                                enum DROP;
                            }
                        }
                    }
                }
            }
        }

        container POLICY_BINDING_TABLE {
            list POLICY_BINDING_TABLE_LIST {
                key INTERFACE_NAME;

                leaf INTERFACE_NAME {
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type string {
                            pattern "Switch";
                        }
                    }
                }

                leaf INGRESS_QOS_POLICY {
                    must "/sonic-flow-based-services/POLICY_TABLE/POLICY_TABLE_LIST[POLICY_NAME=current()]/TYPE = 'QOS'" {
                        error-app-tag policy-not-qos-type;
                        error-message "Policy is not of type qos";
                    }
                    type leafref {
                        path "/sonic-flow-based-services/POLICY_TABLE/POLICY_TABLE_LIST/POLICY_NAME";
                    }
                    sonic-ext:custom-validation ValidateLeafConstant;
                }
                leaf EGRESS_QOS_POLICY {
                    must "/sonic-flow-based-services/POLICY_TABLE/POLICY_TABLE_LIST[POLICY_NAME=current()]/TYPE = 'QOS'" {
                        error-app-tag policy-not-qos-type;
                        error-message "Policy is not of type qos";
                    }
                    type leafref {
                        path "/sonic-flow-based-services/POLICY_TABLE/POLICY_TABLE_LIST/POLICY_NAME";
                    }
                    sonic-ext:custom-validation ValidateLeafConstant;
                }
                leaf INGRESS_MONITORING_POLICY {
                    must "/sonic-flow-based-services/POLICY_TABLE/POLICY_TABLE_LIST[POLICY_NAME=current()]/TYPE = 'MONITORING'" {
                        error-app-tag policy-not-monitoring-type;
                        error-message "Policy is not of type monitoring";
                    }
                    type leafref {
                        path "/sonic-flow-based-services/POLICY_TABLE/POLICY_TABLE_LIST/POLICY_NAME";
                    }
                    sonic-ext:custom-validation ValidateLeafConstant;
                }
                leaf INGRESS_FORWARDING_POLICY {
                    must "/sonic-flow-based-services/POLICY_TABLE/POLICY_TABLE_LIST[POLICY_NAME=current()]/TYPE = 'FORWARDING'" {
                        error-app-tag policy-not-forwarding-type;
                        error-message "Policy is not of type forwarding";
                    }
                    type leafref {
                        path "/sonic-flow-based-services/POLICY_TABLE/POLICY_TABLE_LIST/POLICY_NAME";
                    }
                    sonic-ext:custom-validation ValidateLeafConstant;
                }
            }
        }
    }
}
