module sonic-acl {
    namespace "http://github.com/Azure/sonic-acl";
    prefix sacl;
    yang-version 1.1;

    import ietf-inet-types {
        prefix inet;
    }

    import sonic-common {
        prefix cmn;
    }

    import sonic-extension {
        prefix sonic-ext;
    }

    import sonic-port {
        prefix sprt;
    }

    import sonic-portchannel {
        prefix spc;
    }

    import sonic-vlan {
        prefix svlan;
    }

    import sonic-mirror-session {
        prefix sms;
    }

    organization
        "SONiC";

    contact
        "SONiC";

    description
        "SONIC ACL";

    revision 2020-02-20 {
        description
            "L2 ACL support and update must and when expressions.";
    }

    revision 2019-05-15 {
        description
            "Initial revision.";
    }

    container sonic-acl {

        container ACL_TABLE {

            list ACL_TABLE_LIST {
                key "aclname";
                max-elements 1024; // Max 1K ACL tables for all platforms

                leaf aclname {
                    type string {
                        pattern '[a-zA-Z0-9]{1}([-a-zA-Z0-9_]{0,71})';
                        length 1..72;
                    }
                }

                leaf policy_desc {
                    type string {
                        length 1..255 {
                            error-app-tag policy-desc-invalid-length;
                        }
                    }
                }

                leaf stage {
                    type enumeration {
                        enum INGRESS;
                        enum EGRESS;
                    }
                }

                leaf type {
                    sonic-ext:custom-validation ValidateLeafConstant;
                    type enumeration {
                        enum MIRROR;
                        enum L2;
                        enum L3;
                        enum L3V6;
                        enum TAM;
                    }
                }

                leaf-list ports {
                    type union {
                        type leafref {
                            path "/sprt:sonic-port/sprt:PORT/sprt:PORT_LIST/sprt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type string {
                            pattern "Switch";
                        }
                    }
                }

                must "((/cmn:operation/cmn:operation = 'DELETE') and (count(ports) = 0)) or ((/cmn:operation/cmn:operation != 'DELETE'))" {
                    error-message "ACL actively applied to ports.";
                }
            }
        }

        container ACL_RULE {

            list ACL_RULE_LIST { 
                key "aclname rulename";
                max-elements 65536; // Max 64K ACL rules for all platforms

                leaf aclname {
                    type leafref {
                        path "/sonic-acl/ACL_TABLE/ACL_TABLE_LIST/aclname";
                    }
                } 

                leaf rulename {
                    type string;
                }

                leaf PRIORITY {
                    type uint16 {
                        range "1..65535"{
                            error-message "Invalid ACL rule priority.";
                        }
                    }
                }

                leaf DESCRIPTION {
                    type string;
                }

                leaf PACKET_ACTION {
                    type enumeration {
                        enum FORWARD;
                        enum DROP;
                        enum REDIRECT;
                        enum INT_INSERT;
                        enum INT_DELETE;
                        enum MONITOR_DROPS;
                    }
                }

                leaf MIRROR_ACTION {
                    when "/sonic-acl/ACL_TABLE/ACL_TABLE_LIST[aclname=current()/../aclname]/type = 'MIRROR'";
                    type leafref {
                        path "/sms:sonic-mirror-session/sms:MIRROR_SESSION/sms:MIRROR_SESSION_LIST/sms:name";
                    }
                }

                leaf TAM_INT_TYPE {
                    when "/sonic-acl/ACL_TABLE/ACL_TABLE_LIST[aclname=current()/../aclname]/type = 'TAM'";
                    type enumeration {
                        enum IFA;
                    }
                }

                leaf IP_TYPE {
                    when "(/sonic-acl/ACL_TABLE/ACL_TABLE_LIST[aclname=current()/../aclname]/type = 'L3') or (/sonic-acl/ACL_TABLE/ACL_TABLE_LIST[aclname=current()/../aclname]/type = 'TAM') or (/sonic-acl/ACL_TABLE/ACL_TABLE_LIST[aclname=current()/../aclname]/type = 'L3V6')";

                    sonic-ext:custom-validation ValidateAclRuleIPAddress;
                    type enumeration {
                        enum ANY;
                        enum IP;
                        enum IPV4;
                        enum IPV4ANY;
                        enum NON_IPV4;
                        enum IPV6ANY;
                        enum NON_IPV6;
                    }
                }

                leaf IP_PROTOCOL {
                    when "(/sonic-acl/ACL_TABLE/ACL_TABLE_LIST[aclname=current()/../aclname]/type = 'L3') or (/sonic-acl/ACL_TABLE/ACL_TABLE_LIST[aclname=current()/../aclname]/type = 'TAM') or (/sonic-acl/ACL_TABLE/ACL_TABLE_LIST[aclname=current()/../aclname]/type = 'L3V6')";
                    type uint8;
                }

                leaf ETHER_TYPE {
                    must "(((/sonic-acl/ACL_TABLE/ACL_TABLE_LIST[aclname=current()/../aclname]/type = 'L3') and (current() = '0x800')) or " +
                          "((/sonic-acl/ACL_TABLE/ACL_TABLE_LIST[aclname=current()/../aclname]/type = 'L3V6') and ((current() = '0x86DD') or (current() = '0x86dd'))) or " +
                          "(/sonic-acl/ACL_TABLE/ACL_TABLE_LIST[aclname=current()/../aclname]/type = 'L2'))" {
                          error-message "Ethertype value invalid or not supported for this table type";
                    }
                    type string {
                        pattern "0[xX][6-9a-fA-F][0-9a-fA-F]{2,3}|0[xX][1-9a-fA-F][0-9a-fA-F]{3,4}" {
                            error-message "Invalid Ether Type";
                            error-app-tag ether-type-invalid;
                        }
                    }
                }

                choice src_dst_address {
                    case l2_src_dst_address {
                        when "(/sonic-acl/ACL_TABLE/ACL_TABLE_LIST[aclname=current()/aclname]/type = 'L2') or (/sonic-acl/ACL_TABLE/ACL_TABLE_LIST[aclname=current()/../aclname]/type = 'TAM')";
                        leaf SRC_MAC {
                            type string {
                                pattern "[0-9a-fA-F]{2}(:[0-9a-fA-F]{2}){5}|[0-9a-fA-F]{2}(:[0-9a-fA-F]{2}){5}/[0-9a-fA-F]{2}(:[0-9a-fA-F]{2}){5}";
                            }
                        }
                        leaf DST_MAC {
                            type string {
                                pattern "[0-9a-fA-F]{2}(:[0-9a-fA-F]{2}){5}|[0-9a-fA-F]{2}(:[0-9a-fA-F]{2}){5}/[0-9a-fA-F]{2}(:[0-9a-fA-F]{2}){5}";
                            }
                        }
                    }
                    case ipv4_src_dst_address {
                        when "(/sonic-acl/ACL_TABLE/ACL_TABLE_LIST[aclname=current()/aclname]/type = 'L3') or (/sonic-acl/ACL_TABLE/ACL_TABLE_LIST[aclname=current()/aclname]/type = 'TAM')";
                        leaf SRC_IP {
                            type inet:ipv4-prefix;
                        }
                        leaf DST_IP {
                            type inet:ipv4-prefix;
                        }
                    }
                    case ipv6_src_dst_address {
                        when "(/sonic-acl/ACL_TABLE/ACL_TABLE_LIST[aclname=current()/aclname]/type = 'L3V6') or (/sonic-acl/ACL_TABLE/ACL_TABLE_LIST[aclname=current()/aclname]/type = 'TAM')";
                        leaf SRC_IPV6 {
                            type inet:ipv6-prefix;    
                        }
                        leaf DST_IPV6 {
                            type inet:ipv6-prefix;    
                        }
                    }
                }

                choice src_port {
                    when "(IP_PROTOCOL = '6') or (IP_PROTOCOL = '17')";
                    case l4_src_port {
                        leaf L4_SRC_PORT {
                            type uint16;
                        }
                    }
                    case l4_src_port_range {
                        leaf L4_SRC_PORT_RANGE {
                            type string {
                                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
                            }
                        }
                    }
                }

                choice dst_port {
                    when "(IP_PROTOCOL = '6') or (IP_PROTOCOL = '17')";
                    case l4_dst_port {
                        leaf L4_DST_PORT {
                            type uint16;
                        }
                    }
                    case l4_dst_port_range {
                        leaf L4_DST_PORT_RANGE {
                            type string {
                                pattern "([0-9]{1,4}|[1-5][0-9]{4}|6[0-4][0-9]{3}|65[0-4][0-9]{2}|655[0-2][0-9]|6553[0-5])(-)([0-9]{1,4}|[1-5][0-9]{4}|6[0-4][0-9]{3}|65[0-4][0-9]{2}|655[0-2][0-9]|6553[0-5])";
                            }
                        }
                    }
                }

                leaf TCP_FLAGS {
                    when "current()/../IP_PROTOCOL = '6'";
                    type string {
                        pattern "0[xX][0-9a-fA-F]{2}[/]0[xX][0-9a-fA-F]{2}";
                    }
                }

                leaf ICMP_TYPE {
                    when "(current()/../IP_PROTOCOL = '1') or ((current()/../IP_PROTOCOL = '58'))";
                    type uint8;
                }

                leaf ICMP_CODE {
                    when "(current()/../IP_PROTOCOL = '1') or ((current()/../IP_PROTOCOL = '58'))";
                    type uint8;
                }

                leaf DSCP {
                    when "(/sonic-acl/ACL_TABLE/ACL_TABLE_LIST[aclname=current()/../aclname]/type = 'L3') or (/sonic-acl/ACL_TABLE/ACL_TABLE_LIST[aclname=current()/../aclname]/type = 'L3V6') or (/sonic-acl/ACL_TABLE/ACL_TABLE_LIST[aclname=current()/../aclname]/type = 'TAM')";
                    type uint8 {
                        range "0..63"{
                            error-message "Invalid DSCP Value.";
                        }
                    }
                }
                
                leaf VLAN {
                    type uint16 {
                        range "1..4094" {
                            error-message "Vlan ID out of range";
                            error-app-tag vlanid-invalid;
                        }
                    }
                }

                leaf PCP {
                    when "(/sonic-acl/ACL_TABLE/ACL_TABLE_LIST[aclname=current()/aclname]/type = 'L2') or (/sonic-acl/ACL_TABLE/ACL_TABLE_LIST[aclname=current()/../aclname]/type = 'TAM')";
                    type string {
                        pattern "[0-7]|[0-7]/[0-7]" {
                            error-message "Invalid PCP Value.";
                        }
                    }
                }

                leaf DEI {
                    when "(/sonic-acl/ACL_TABLE/ACL_TABLE_LIST[aclname=current()/aclname]/type = 'L2') or (/sonic-acl/ACL_TABLE/ACL_TABLE_LIST[aclname=current()/../aclname]/type = 'TAM')";
                    type uint8 {
                        range "0..1" {
                            error-message "Invalid DEI Value.";
                        }
                    }
                }
            }
        }
    }
}
