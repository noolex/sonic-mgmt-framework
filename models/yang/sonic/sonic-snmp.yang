module sonic-snmp {
  namespace "http://github.com/Azure/sonic-snmp";
  prefix ssnmp;
  yang-version 1;

  import ietf-yang-types {
    prefix yang;
  }

  import ietf-inet-types {
    prefix inet;
  }

  organization
    "SONiC";

  contact
    "SONiC";

  description
    "SONIC SNMP";

  revision 2019-11-12 {
    description
      "Initial revision.";
  }

  /* Definitions from ietf-snmp-common.yang. That model cannot be imported
     because it "belongs" to ietf-snmp.
   */
  typedef admin-string {
    type string {
      length "0..255";
    }
    description
      "Represents SnmpAdminString as defined in RFC 3411.

      Note that the size of an SnmpAdminString is measured in
      octets, not characters.";

    reference
      "RFC 3411: An Architecture for Describing Simple Network
         Management Protocol (SNMP) Management Frameworks.
         SNMP-FRAMEWORK-MIB.SnmpAdminString";
  }

  typedef identifier {
    type admin-string {
      length "1..32";
    }
    description
      "Identifiers are used to name items in the SNMP configuration
      datastore.";
  }

  typedef context-name {
    type admin-string {
      length "0..32";
    }
    description
      "The context type represents an SNMP context name.";
    reference
      "RFC 3411: An Architecture for Describing Simple Network
         Management Protocol (SNMP) Management Frameworks";
  }

  typedef security-name {
    type admin-string {
      length "1..32";
    }
    description
      "The security-name type represents an SNMP security name.";
    reference
      "RFC 3411: An Architecture for Describing Simple Network
         Management Protocol (SNMP) Management Frameworks";
  }

  typedef security-model {
    type union {
      type enumeration {
        enum v2c { value 2; }
        enum usm { value 3; }
        enum tsm { value 4; }
      }
      type int32 {
        range "1..2147483647";
      }
    }
    reference
      "RFC 3411: An Architecture for Describing Simple Network
         Management Protocol (SNMP) Management Frameworks";
  }

  typedef security-model-or-any {
    type union {
      type enumeration {
        enum any { value 0; }
      }
      type security-model;
    }
    reference
      "RFC 3411: An Architecture for Describing Simple Network
         Management Protocol (SNMP) Management Frameworks";
  }

  typedef security-level {
    type enumeration {
      enum no-auth-no-priv { value 1; }
      enum auth-no-priv    { value 2; }
      enum auth-priv       { value 3; }
    }
    reference
      "RFC 3411: An Architecture for Describing Simple Network
         Management Protocol (SNMP) Management Frameworks";
  }

  typedef engine-id {
    type yang:hex-string {
      pattern '([0-9a-fA-F]){2}(:([0-9a-fA-F]){2}){4,31}';
    }
    description
      "The engine ID specified as a list of colon-specified
      hexadecimal octets, e.g., '80:00:02:b8:04:61:62:63'.";
    reference
      "RFC 3411: An Architecture for Describing Simple Network
         Management Protocol (SNMP) Management Frameworks";
  }

  typedef wildcard-object-identifier {
    type string;
    description
      "The wildcard-object-identifier type represents an SNMP object
      identifier where subidentifiers can be given either as a label,
      in numeric form, or a wildcard, represented by an asterisk
      ('*').";
  }

  typedef tag-value {
    type string {
      length "0..255";
    }
    description
      "Represents SnmpTagValue as defined in RFC 3413.

      Note that the size of an SnmpTagValue is measured in
      octets, not characters.";
    reference
      "RFC 3413: Simple Network Management Protocol (SNMP)
         Applications.
         SNMP-TARGET-MIB.SnmpTagValue";
  }

  typedef view-name {
    type ssnmp:identifier;
    description
      "The view-name type represents an SNMP VACM view name.";
  }

  typedef group-name {
    type ssnmp:identifier;
    description
      "The group-name type represents an SNMP VACM group name.";
  }

  container sonic-snmp {

		container SNMP_SERVER_COMMUNITY {
      list SNMP_SERVER_COMMUNITY_LIST {
        key index;
        description
          "List of communities.";

        leaf index {
          type identifier;
          description
            "Index into the community list which must be the community name.";
        }

        leaf securityName {
          type security-name;
          description
            "The group this community is a member of. For communities with no
             group association, securityName should be set to 'None'.";
        }
      }
    }

    container SNMP_SERVER_VIEW {
      list SNMP_SERVER_VIEW_LIST {
        key name;
        description
          "Definition of MIB views.";

        leaf name {
          type view-name;
          description
            "The name of this VACM MIB view.";
        }

        leaf-list include {
          type wildcard-object-identifier;
          description
            "A family of subtrees included in this MIB view.";
        }

        leaf-list exclude {
          type wildcard-object-identifier;
          description
            "A family of subtrees excluded in this MIB view.";
        }
      }
    }

    container SNMP_SERVER_GROUP {
      list SNMP_SERVER_GROUP_LIST {
        key name;
        description
          "VACM groups.

           Groups are explicitly defined in this list. Group members are defined
           in the 'member' list and access for the group is defined in the
           'access' list.";

        leaf name {
          type group-name;
          description
            "The name of this SNMP VACM group.";
        }
      }
    }

    container SNMP_SERVER_GROUP_MEMBER {
      list SNMP_SERVER_GROUP_MEMBER_LIST {
        key "groupName securityName";
        description
          "A member of this VACM group.

           A specific combination of securityName and securityModel MUST NOT be
           present in more than one group.";

        leaf groupName {
          description "SNMP VACM group name.";
          type leafref {
            path "/ssnmp:sonic-snmp/SNMP_SERVER_GROUP/SNMP_SERVER_GROUP_LIST/name";
          }
        }

        leaf securityName {
          type security-name;
          description
            "The securityName of a group member.";
        }

        leaf securityModel {
          type security-model;
          description
            "The security models under which this securityName is a member of this group.";
        }
      }
    }

    container SNMP_SERVER_GROUP_ACCESS {
      list SNMP_SERVER_GROUP_ACCESS_LIST {
        key "groupName context securityModel securityLevel";
        description
          "Definition of access rights for VACM group.";

        leaf groupName {
          description "SNMP group name";
          type leafref {
            path "/ssnmp:sonic-snmp/SNMP_SERVER_GROUP/SNMP_SERVER_GROUP_LIST/name";
          }
        }

        leaf context {
          type context-name;
          description
            "The context under which the access rights apply. For this version, this MUST be 'Default'.";
        }

        leaf contextMatch {
          type enumeration {
            enum exact { value 1; }
            enum prefix { value 2; }
          }
          default "exact";
        }

        leaf securityModel {
          type security-model-or-any;
          description
            "The security model under which the access rights apply.";
        }

        leaf securityLevel {
          type security-level;
          description
            "The minimum security level under which the access rights apply.";
        }

        leaf readView {
          type view-name;
          description
            "The name of the MIB view authorizing read access.";
        }

        leaf writeView {
          type view-name;
          description
            "The name of the MIB view authorizing write access. As the MIBs are currently read-only, the value of this view-name is immaterial.";
        }

        leaf notifyView {
          type view-name;
          description
            "The name of the MIB view authorizing notify access.";
        }
      }
    }

    container SNMP_SERVER_USER {
      list SNMP_SERVER_USER_LIST {
        key name;
        description
          "SNMPv3 user list.";

        leaf name {
          type identifier;
          description
            "SNMPv3 user name.";
        }

        leaf shaKey {
          type yang:hex-string;
          description
            "The presence of this key enables SHA authentication for the user.";
        }

        leaf md5Key {
          type yang:hex-string;
          description
            "The presence of this key enables MD5 authentication for the user.";
        }

        leaf desKey {
          type yang:hex-string;
          description
            "The presence of this key enables DES encryption for the user.";
        }

        leaf aesKey {
          type yang:hex-string;
          description
            "The presence of this key enables AES-128 encryption for the user.";
        }
      }
    }

    container SNMP_SERVER_PARAMS {
      list SNMP_SERVER_PARAMS_LIST {
        key name;
        description
          "List of target parameters.";

        leaf name {
          type identifier;
          description
            "The name associated to the target parameters. This needs to match
             targetParams from the associated entry in the SNMP_SERVER_TARGET
             list.";
        }

        leaf securityNameV2 {
          type security-name;
          description
            "The community name of the SNMPv2 target entry.";
        }

        leaf user {
          type security-name;
          description
            "The user name of the SNMPv3 target entry.";
        }

        leaf security-level {
          type security-level;
          description
            "The security level of the SNMPv3 target entry.";
        }
      }
    }

    container SNMP_SERVER_TARGET {
      list SNMP_SERVER_TARGET_LIST {
        key name;
        description
          "List of targets.";

        leaf name {
          type identifier;
          description
            "Administrative name of the target entry.";
        }

        leaf-list tag {
          type tag-value;
          description
            "Tag values used to select target addresses. Should be one of
             TrapNotify or InformNotify.";
        }

        leaf timeout {
          type uint32;
          units "0.01 seconds";
          description
            "Needed only if this target can receive InformRequest-PDUs.";
        }

        leaf retries {
          type uint8;
          description
            "Needed only if this target can receive InformRequest-PDUs.";
        }

        leaf targetParams {
          description
            "The name associated to the target parameters. This needs to match
             the name from the associated entry in the SNMP_SERVER_PARAMS list.";
          type leafref {
            path "/ssnmp:sonic-snmp/SNMP_SERVER_PARAMS/SNMP_SERVER_PARAMS_LIST/name";
          }
        }

        leaf ip {
          type inet:ip-address;
          description
            "The IPv4 or IPv6 address of the target.";
        }

        leaf port {
          type inet:port-number;
          description
            "UDP port number.";
        }
      }
    }

    container SNMP_SERVER_ENGINE {
      list SNMP_SERVER_ENGINE_LIST {
        key "id";

        leaf id {
          type enumeration {
            enum GLOBAL;
          }
        }

        leaf enabled {
          type boolean;
          description
            "Enables the SNMP engine. This is always true";
        }

        leaf engine-id {
          type engine-id;
          description
            "The local SNMP engine's administratively assigned unique
             identifier. If this leaf is not set, the device automatically
             calculates an engine ID, as described in RFC 3411.";
        }
      }
    }

  }
}
