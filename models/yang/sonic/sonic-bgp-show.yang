module sonic-bgp-show {
    namespace "http://github.com/Azure/sonic-bgp-show";
    prefix sbgpshow;
    yang-version 1.1;

    import ietf-inet-types { prefix inet; }

    organization
        "SONiC";

    contact
        "SONiC";

    description
        "SONiC yang for RPC based BGP show.";

    revision 2020-01-20 {
        description
            "Initial revision.";
    }

    typedef route-path-query-type {
        description "Query type to fetch paths for a particular route prefix";

        type enumeration {
            enum BEST_PATH {
                description "To query best path for a particular route prefix";
            }
            enum MULTI_PATH {
                description "To query multiple paths for a particular route prefix";
            }
        }
    }

    typedef show-bgp-query-type {
        description "Query type that specifies the various ways to fetch the BGP-routes based on the various filters";

        type enumeration {
            enum ALL {
                description "To query all BGP routes";
            }
            enum IP-ADDR {
                description "To query the BGP routes that matches IP-address";
            }
            enum COMMUNITY-STRING {
                description "To query the BGP routes that matches community-string";
            }
            enum COMMUNITY-LOCAL-AS {
                description "To query the BGP routes that matches community local-AS";
            }
            enum COMMUNITY-NO-ADVERTISE {
                description "To query the BGP routes that matches community no-advertise";
            }
            enum COMMUNITY-NO-EXPORT {
                description "To query the BGP routes that matches community no-export";
            }
            enum COMMUNITY-NO-PEER {
                description "To query the BGP routes that matches community no-peer";
            }
            enum ROUTE-MAP {
                description "To query the BGP routes that matches route-map";
            }
        }
    }

    rpc show-bgp {

        description "RPC for fetch BGP routes based on various different options";

        input {
            leaf vrf-name {
                type string;
                default "default";
                description
                    "Fetches BGP routes for given VRF name. If VRF name is not present, the default VRF is used";
            }

            leaf address-family {
                type enumeration {
                    enum IPV4_UNICAST;
                    enum IPV6_UNICAST;
                }
                default "IPV4_UNICAST";
                description
                    "Address family(IPv4/IPv6)";
            }

            leaf query-type {
                type show-bgp-query-type;
                default "ALL";
                description
                    "Query type that specifies the various ways to fetch the BGP-routes based on the various filters.
                    It represent the choice mentioned below. And then relevant attributes should be filled to fetch the BGP routes.";
            }

            choice type {
                case ip {
                    description
                        "query-type attribute should be IP-ADDR. Fetch the route prefixes that matches the IPv4/IPv6 address";

                    leaf ip-addr {
                        type inet:ip-address;
                        mandatory true;
                        description "The IPv4/Ipv6 address";
                    }

                    leaf path-type {
                        type route-path-query-type;
                        default "MULTI_PATH";
                        description "Query type to fetch paths for a particular route prefix";
                    }
                }

                case community-str {
                    description
                        "query-type attribute should be COMMUNITY-STRING. Fetch the route prefixes that matches community-string";

                    leaf community-string {
                        type string;
                        mandatory true;
                        description "Community string in AA:BB format";
                    }

                    leaf community-str-exact-match {
                        type boolean;
                        default false;
                        description "True : to fetch BGP routes that matches this community-string alone";
                    }
                }
                case community-local-as {
                    description
                        "query-type attribute should be COMMUNITY-LOCAL-AS. Fetch the route prefixes that matches community local-AS";

                    leaf community-local-as-exact-match {
                        type boolean;
                        default false;
                        description "True : to fetch BGP routes that matches community local-AS alone";
                    }
                }
                case community-no-advertise {
                    description
                        "query-type attribute should be COMMUNITY-NO-ADVERTISE. Fetch the route prefixes that matches community no-advertise";

                    leaf community-no-advertise-exact-match {
                        type boolean;
                        default false;
                        description "True : to fetch BGP routes that matches community no-advertise alone";
                    }
                }
                case community-no-export {
                    description
                        "query-type attribute should be COMMUNITY-NO-EXPORT. Fetch the route prefixes that matches community no-export";

                    leaf community-no-export-exact-match {
                        type boolean;
                        default false;
                        description "True : to fetch BGP routes that matches community no-export alone";
                    }
                }
                case community-no-peer {
                    description
                        "query-type attribute should be COMMUNITY-NO-PEER. Fetch the route prefixes that matches community no-peer";

                    leaf community-no-peer-exact-match {
                        type boolean;
                        default false;
                        description "True : to fetch BGP routes that matches community no-peer alone";
                    }
                }
                case route-map {
                    description
                        "query-type attribute should be ROUTE-MAP. Fetch the route prefixes that matches this route-map";

                    leaf route-map-name {
                        type string;
                        mandatory true;
                        description "True : to fetch BGP routes that matches this route-map";
                    }
                }
            }
        }

        output {
            leaf status {
                type string;
                description
                    "On success, returns all BGP routes in JSON string format.";
            }
        }
    }

    rpc show-bgp-statistics {

        description "RPC to fetch the BGP statistics";

        input {
            leaf vrf-name {
                type string;
                default "default";
                description
                    "Fetches BGP statistics for given VRF name. if VRF name is not present, the default VRF is used";
            }

            leaf address-family {
                type enumeration {
                    enum IPV4_UNICAST;
                    enum IPV6_UNICAST;
                }
                default "IPV4_UNICAST";
                description
                    "Address family(IPv4/IPv6)";
            }
        }

        output {
            leaf status {
                type string;
                description
                    "On success, returns all BGP routes in JSON string format.";
            }
        }
    }
}
