module sonic-ospfv2 {
  namespace "http://github.com/Azure/sonic-ospfv2";
  prefix sn-ospfv2;
  yang-version 1.1;

  import ietf-yang-types { 
    prefix "ietf-yang"; 
  }

  import ietf-inet-types { 
    prefix "ietf-inet"; 
  }

  import sonic-ospfv2-common { 
    prefix "sonic-ospf-cmn"; 
  }

  import sonic-vrf { 
    prefix "sonic-vrf"; 
  }

  import sonic-route-map { 
    prefix "sonic-rmap";
  }

  import sonic-routing-policy-sets {
      prefix "sonic-rpolicy";
  }

  organization
    "SONiC";

  contact
    "SONiC";

  description
     "SONIC ospfv2 Global YANG";

  revision 2020-03-21 {
    description
      "Added Yang definition for OSPFv2 features.";
  }

 

  container sonic-ospfv2 {  

    container OSPFV2_ROUTER {
      description
        "OSPFv2 router global configuration Table.";

      list OSPFV2_ROUTER_LIST {

        key "vrf_name";

        leaf vrf_name {
          type union {
            type string {
              pattern "default";
            }
            type leafref {
              path "/sonic-vrf:sonic-vrf/sonic-vrf:VRF/sonic-vrf:VRF_LIST/sonic-vrf:vrf_name";
            }
          }
        }

        leaf enable {
          type boolean;
          description
            "OSPFv2 router is enabled in thsi VRF";
        }

        leaf description {
          type string;
           description
             "String description for the configured router";
           default "OSPFv2 Router";
        }

        leaf router-id {
          type ietf-yang:dotted-quad;
          description
            "OSPF router Id";
        }

        leaf abr-type {
          type sonic-ospf-cmn:ospf-abr-type;
          description
            "OPSF ABR type";
        }

        leaf auto-cost-reference-bandwidth {
          type uint32 {
            range "1..4294967";
          }
          description
            "Refrence Bandwidth for auto calculating OSPFv2 interface cost.";
        }

        leaf log-adjacency-changes {
          type sonic-ospf-cmn:ospf-log-type;
          description
            "OPSF adjacency event logging";
          default LOG_NONE;
        }

        leaf default-metric {
          type uint32;
          description
            "Default metric value for routes";
        }

        leaf opaque-lsa-capability {
          type boolean;
          description
            "When the value of this leaf is set to true, opaque LSA
             capability (rfc2370) is enabled.";
        }

        leaf ospf-rfc1583-compatible {
          type boolean;
          description
            "OSPF RFC1538 comaptible";
          default false;
        }

        leaf passive-interface-default {
          type boolean;
          description
            "OSPF configuration for default passive interface";
          default false;
        }

        leaf write-multiplier {
          type uint8 {
             range "0..100";
          }
          description
            "OSPFv2 write multiplier";
        }

        leaf spf-initial-delay {
          type uint32 {
            range "0..600000";
          }
          description
            "SPF initial Delay";
        }

        leaf spf-maximum-delay {
          type uint32 {
            range "0..600000";
          }
          description
            "SPF maximum Delay";
        }

        leaf spf-throttle-delay {
          type uint32 {
            range "0..600000";
          }
          description
            "SPF throttle Delay";
        }

        leaf lsa-min-interval-timer {
          type uint32 {
            range "0..50000";
          }
          description
            "SA minimum interval timer";
        }

        leaf lsa-min-arrival-timer {
          type uint32 {
            range "0..50000";
          }
          description
            "LSA minimum arrival timer";
        }

        leaf lsa-refresh-timer {
          type uint32 {
            range "10..1800";
          }
          description
            "SPF throttle Delay";
        }

        leaf max-metric-administrative {
          type boolean;
          description
            "OSPF Max-metric is administrative configuration";
          default false;
        }

        leaf max-metric-on-startup {
          type uint32 {
            range "5..86400";
          }
          units seconds;
          description
            "Max metric startup timeout in seconds";
        }

        leaf max-metric-on-shutdown {
          type uint32 {
            range "5..500";
          }
          units seconds;
          description
            "Max metric shutdown timeout in seconds";
        }

        leaf distance-all {
          type sonic-ospf-cmn:ospf-distance;
          description
            "Distribute distance for all routes ";
        }

        leaf distance-intra-area {
          type sonic-ospf-cmn:ospf-distance;
          description
            "Distribute distance for intra area routes";
        }

        leaf distance-inter-area {
          type sonic-ospf-cmn:ospf-distance;
          description
            "Distribute distance for inter area routes";
        }

        leaf distance-external {
          type sonic-ospf-cmn:ospf-distance;
          description
            "Distribute distance for external routes";
        }

      } //OSPFV2_ROUTER_LIST
    } //OSPFV2_ROUTER



    container OSPFV2_ROUTER_AREA {
      description
        "OSPFv2 Area configuration table.";

      list OSPFV2_ROUTER_AREA_LIST {

        key "vrf_name area-id";

        leaf vrf_name {
          type leafref {
            path "../../../OSPFV2_ROUTER/OSPFV2_ROUTER_LIST/vrf_name";
          }
        }

        leaf area-id {
          type sonic-ospf-cmn:ospf-area-identifier;
        }

        leaf description {
          type string;
           description
             "String description for the configured area";
           default "OSPFv2 Area";
        }

        leaf authentication {
          type string;
          description
            "OSPFv2 Area level authentication type.";
        }

        leaf stub {
          type boolean;
          description
            "OSPFv2 stub configuration.";
        }

        leaf stub-no-summary {
          type boolean;
          description
            "OSPFv2 stub no summummary.";
        }

        leaf stub-default-cost {
          type uint32;
          description
            "OSPFv2 stub default cost.";
        }


        leaf import-list {
          type leafref {
            path "/sonic-rmap:sonic-route-map/sonic-rmap:ROUTE_MAP_SET" +
                 "/sonic-rmap:ROUTE_MAP_SET_LIST/sonic-rmap:name";
          }
          description
            "OSPFv2 Area policy import route map name.";
        }

        leaf export-list {
          type leafref {
            path "/sonic-rmap:sonic-route-map/sonic-rmap:ROUTE_MAP_SET" +
                 "/sonic-rmap:ROUTE_MAP_SET_LIST/sonic-rmap:name";
          }
          description
            "OSPFv2 Area policy export route map name.";
        }

        leaf filter-list-in {
          type leafref {
            path "/sonic-rpolicy:sonic-routing-policy-sets/sonic-rpolicy:PREFIX_SET" +
                 "/sonic-rpolicy:PREFIX_SET_LIST/sonic-rpolicy:name";
          }
          description
            "OSPFv2 Area policy import filter list name.";
        }

        leaf filter-list-out {
          type leafref {
            path "/sonic-rpolicy:sonic-routing-policy-sets/sonic-rpolicy:PREFIX_SET" +
                 "/sonic-rpolicy:PREFIX_SET_LIST/sonic-rpolicy:name";
          }
          description
            "OSPFv2 Area policy export filter list name.";
        }


      } //OSPFV2_ROUTER_AREA_LIST
    } //OSPFV2_ROUTER_AREA

    

    container OSPFV2_ROUTER_AREA_NETWORK {
      description
        "OSPFv2 Area Network prefix configuration table.
         Interface with IPv4 address matching the network 
         prefix is considered to be part of current area";

      list OSPFV2_ROUTER_AREA_NETWORK_LIST {

        key "vrf_name area-id prefix";

        leaf vrf_name {
          type leafref {
            path "../../../OSPFV2_ROUTER/OSPFV2_ROUTER_LIST/vrf_name";
          }
        }

        leaf area-id {
          type sonic-ospf-cmn:ospf-area-identifier;
          /*
          type leafref {
            path "../../../OSPFV2_ROUTER_AREA/OSPFV2_ROUTER_AREA_LIST[vrf_name=current()/../vrf_name]/area-id";
          }
          */
        }

        leaf prefix {
           type ietf-inet:ipv4-prefix;
           description
             "Network address prefix of the OSPF interface
              Interface with IPv4 address matching the network
              prefix is considered to be part of current area";
        }

        leaf description {
          type string;
           description
             "String description for the configured prefix";
           default "Network address";
        }

      } //OSPFV2_ROUTER_AREA_NETWORK_LIST
    } //OSPFV2_ROUTER_AREA_NETWORK


    container OSPFV2_ROUTER_AREA_VIRTUAL_LINK {
      description
        "OSPFv2 Area Virtual Link configuration table.";

      list OSPFV2_ROUTER_AREA_VIRTUAL_LINK_LIST {

        key "vrf_name area-id remote-router-id";

        leaf vrf_name {
          type leafref {
            path "../../../OSPFV2_ROUTER/OSPFV2_ROUTER_LIST/vrf_name";
          }
        }

        leaf area-id {
          type sonic-ospf-cmn:ospf-area-identifier;
          /*
          type leafref {
            path "../../../OSPFV2_ROUTER_AREA/OSPFV2_ROUTER_AREA_LIST[vrf_name=current()/../vrf_name]/area-id";
          }
          */
        }

        leaf description {
          type string;
           description
             "String description for the configured virtual link";
           default "Virtual Link";
        }

        leaf remote-router-id {
          type ietf-yang:dotted-quad;
          description
            "The router ID of the remote OSPFv2 ABR router.";
        }

        leaf authentication-type {
          type sonic-ospf-cmn:ospf-authentication-type;
          default AUTH_NONE;
          description
             "OSPF autentication type";
        }

        leaf authentication-key {
          type string;
          description
            "OSPF authentication password string.";
        }

        leaf authentication-key-id {
          // when "../authentication-type = 'sonic-ospf-cmn:MD5HMAC'";
          type uint8;
          description
            "Authentication key Id";
        }

        leaf authentication-md5-key {
          type string;
          description
            "OSPF authentication md5 password string.";
        }

        leaf dead-interval {
          type uint32;
          units seconds;
          description
            "The number of seconds that the local system should let
            elapse before declaring a silent router down";
          default 40;
        }

        leaf hello-interval {
          type uint32;
          units seconds;
          description
            "The number of seconds the local system waits between the
            transmission of subsequent Hello packets";
          default 10;
        }

        leaf retransmission-interval {
          type uint32;
          units seconds;
          description
            "The number of seconds that the local system waits before
            retransmitting an unacknowledged LSA.";
          default 5;
        }

        leaf transmit-delay {
          type uint32 {
            range 1..65535;
          }
          units seconds;
          description
            "The number of seconds that the local system waits before
            retransmitting an unacknowledged LSA.";
        }
      } //OSPFV2_ROUTER_AREA_VIRTUAL_LINK_LIST
    } //OSPFV2_ROUTER_AREA_VIRTUAL_LINK


    container OSPFV2_ROUTER_AREA_POLICY_ADDRESS_RANGE {
      description
        "OSPFv2 inter area policy address range configuartion
         Table.";

      list OSPFV2_ROUTER_AREA_POLICY_ADDRESS_RANGE_LIST {

        key "vrf_name area-id prefix";

        leaf vrf_name {
          type leafref {
            path "../../../OSPFV2_ROUTER/OSPFV2_ROUTER_LIST/vrf_name";
          }
        }

        leaf area-id {
          type sonic-ospf-cmn:ospf-area-identifier;
          /*
          type leafref {
            path "../../../OSPFV2_ROUTER_AREA/OSPFV2_ROUTER_AREA_LIST[vrf_name=current()/../vrf_name]/area-id";
          }
          */
        }

        leaf prefix {
          type ietf-inet:ipv4-prefix;
          description
            "Address prefix for the OSPF address";
        }

        leaf description {
          type string;
           description
             "String description for the configured address range";
           default "Address range";
        }

        leaf advertise {
          type boolean;
          description
            "Advertise or no-adverise configuration for prefix";
          default true;
        }

        leaf metric {
          type sonic-ospf-cmn:ospf-metric;
          description
            "Metric value for the prefix";
        }

        leaf substitute {
          type boolean;
          description
            "Substitute Address prefix for the OSPF address";
          default false;
        }

        leaf substitue-prefix {
          type ietf-inet:ipv4-prefix;
          description
            "Substitute Address prefix for the OSPF address";
        }

      } //OSPFV2_ROUTER_AREA_POLICY_ADDRESS_RANGE_LIST
    } //OSPFV2_ROUTER_AREA_POLICY_ADDRESS_RANGE


    container OSPFV2_ROUTER_DISTRIBUTE_ROUTE {
      description
        "OSPFv2 policy route distribution Table.";

      list OSPFV2_ROUTER_DISTRIBUTE_ROUTE_LIST {

        key "vrf_name protocol direction";

        leaf vrf_name {
          type leafref {
            path "../../../OSPFV2_ROUTER/OSPFV2_ROUTER_LIST/vrf_name";
          }
        }

        leaf protocol {
          type sonic-ospf-cmn:ospf-policy-protocol;
          description
            "Distribute routes to or from protocol";
        }

        leaf direction {
          type sonic-ospf-cmn:ospf-policy-direction;
          description
            "Ditribute type or direction IMPORT or EXPORT";
        }

        leaf description {
          type string;
           description
             "String description for the configured policy";
           default "Route distribution policy";
        }

        leaf metric {
          type sonic-ospf-cmn:ospf-metric;
          description
            "Metric for route distribution";
        }

        leaf metric-type {
          type sonic-ospf-cmn:ospf-metric-type;
          description
            "Metric type for route distribution";
        }

        leaf table-id {
          //when "../protocol = 'sonic-ospf-cmn:OSPF'" ;
          type uint32;
          description
            "Distribute OSPF protocol routing table instance id";
        }

        leaf always {
          //when "../protocol = 'sonic-ospf-cmn:DEFAULT_ROUTE' or ../protocol = 'DEFAULT_ROUTE'" ;
          type boolean ;
          description
            "Distribute default-route is always or not";
        }

        leaf route-map {
          type leafref {
            path "/sonic-rmap:sonic-route-map/sonic-rmap:ROUTE_MAP_SET" +
                 "/sonic-rmap:ROUTE_MAP_SET_LIST/sonic-rmap:name";
          }
          description
            "Route map for default route originate or distribution";
        }
      } //OSPFV2_ROUTER_DISTRIBUTE_ROUTE_LIST
    } //OSPFV2_ROUTER_DISTRIBUTE_ROUTE


    container OSPFV2_INTERFACE {
       description
         "OSPFv2 Interface Table.";

       list OSPFV2_INTERFACE_LIST {

         key "name";

         leaf name {
           type sonic-ospf-cmn:ospf-interface;
           description
             "OPSF interface";
         }

         leaf vrf_name {
           type union {
             type string {
               pattern "default";
             }
             type leafref {
               path "/sonic-vrf:sonic-vrf/sonic-vrf:VRF/sonic-vrf:VRF_LIST/sonic-vrf:vrf_name";
             }
           }
           default "default";
         }

         leaf area-id {
           type sonic-ospf-cmn:ospf-area-identifier;
           description
             "An identifier for the OSPFv2 area - described as either a
             32-bit unsigned integer, or a dotted-quad";
         }

         leaf address {
           type ietf-inet:ipv4-address-no-zone;
           description
             "The Interface address";
         }

         leaf network-type {
           type sonic-ospf-cmn:ospf-network-type;
           description
             "Network type for the interface";
         }

         leaf metric {
           type sonic-ospf-cmn:ospf-metric;
           description
             "The metric for the interface";
         }

         leaf priority {
           type uint8;
           description
             "The local system's priority to become the designated router";
         }

         leaf passive {
           type boolean;
           description
             "When this leaf is set to true, the interface should be
             advertised within the OSPF area but OSPF adjacencies should
             not be established over the interface";
         }

         leaf passive-interface-address {
           type ietf-inet:ipv4-address-no-zone;
           description
             "The Interface address";
         }

         leaf mtu-ignore {
           type boolean;
           description
              "OSPF interface MTU ignore configuration.";
         }

         leaf bfd-enable {
           type boolean;
           description
              "OSPF interface BFD configuration.";
         }

         leaf authentication-type {
           type sonic-ospf-cmn:ospf-authentication-type;
           default AUTH_NONE;
           description
              "OSPF autentication type";
         }

         leaf authentication-key {
           type string;
           description
             "OSPF authentication password string.";
         }

         leaf authentication-key-id {
           //when "../authentication-type = 'sonic-ospf-cmn:MD5HMAC'";
           type uint8;
           description
             "Authentication key Id";
         }

         leaf authentication-md5-key {
           type string;
           description
             "OSPF authentication md5 password string.";
         }

         leaf dead-interval {
           type uint32;
           units seconds;
           description
             "The number of seconds that the local system should let
             elapse before declaring a silent router down";
           default 40;
         }

         leaf hello-interval {
           type uint32;
           units seconds;
           description
             "The number of seconds the local system waits between the
             transmission of subsequent Hello packets";
           default 10;
         }

         leaf hello-multiplier {
           type uint32 {
             range 1..10;
           }
           description
              "OSPF interface hello multiplier configuration.";
         }

         leaf retransmission-interval {
           type uint32;
           units seconds;
           description
             "The number of seconds that the local system waits before
             retransmitting an unacknowledged LSA.";
           default 5;
         }

         leaf transmit-delay {
           type uint32 {
             range 1..65535;
           }
           units seconds;
           description
             "The number of seconds that the local system waits before
             retransmitting an unacknowledged LSA.";
         }

       } //OSPFV2_INTERFACE_LIST
     } //OSPFV2_INTERFACE




  } //sonic-ospfv2
}
