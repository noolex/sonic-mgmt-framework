module sonic-client-auth {
    namespace "http://github.com/Azure/sonic-client-auth";
    prefix sclauth;
    yang-version 1.1;

    organization
        "SONiC";

    contact
        "SONiC";

    description
        "SONiC Client Auth";

    revision 2020-04-07 {
        description
            "Initial revision.";
    }

    container sonic-client-auth {
        container REST_SERVER {
            list REST_SERVER_LIST {
                key "server";
                leaf server {
                    type string {
                        pattern "default";
                    }
                }
                leaf client_auth {
                    type string {
                        pattern "((password|cert|jwt|none),?)*" {
                            error-message "Invalid Rest client_auth pattern";
                            error-app-tag client-auth-invalid;
                        }
                    }
                }
            }
        }
        container TELEMETRY {
            list TELEMETRY_LIST {
                key "server";
                leaf server {
                    type string {
                        pattern "gnmi";
                    }
                }
                leaf client_auth {
                    type string {
                        pattern "((password|cert|jwt|none),?)*" {
                            error-message "Invalid GNMI client_auth pattern";
                            error-app-tag client-auth-invalid;
                        }
                    }
                }
            }
        }
    }
}
