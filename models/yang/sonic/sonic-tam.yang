module sonic-tam {
    namespace "http://github.com/Azure/sonic-tam";
    prefix tam;

    import ietf-inet-types {
        prefix inet;
    }

    organization
        "SONiC";

    contact
        "SONiC";

    description
        "SONIC TAM";

    revision 2019-11-08 {
        description
            "Initial revision.";
    }

    container sonic-tam {

        container TAM_DEVICE_TABLE {

            list TAM_DEVICE_TABLE_LIST {
		description
		    "Information on TAM Device Information.";

                key "name";

                leaf name {

                    type enumeration {
                        enum device;
                    }

                    description
			"Device Identifier.";

                }

                leaf deviceid {
                    type uint16;
                    default 0;

		    description
		       "Uniquely identifies a device on the network to be analyzed.";
                }
            }
        }

        container TAM_COLLECTOR_TABLE {

            list TAM_COLLECTOR_TABLE_LIST {
                key "name";

	        description
	            "Defines TAM collector configuration.";

                leaf name {
                    type string {
                        pattern '[a-zA-Z0-9]{1}([-a-zA-Z0-9_]{0,32})';
                        length 1..32;
                    }

		    description
		       "Collector name should be unique.";
                }

                leaf ipaddress-type {
                    must "(contains(../ipaddress, ':') and current()='ipv6') or
                          (contains(../ipaddress, '.') and current()='ipv4')" {
                        error-message "%Error: Wrong ipaddress for the specified ipaddress-type";
                        error-app-tag invalid-ipaddress;
                    }

                    type enumeration {
                        enum ipv4;
                        enum ipv6;
                    }

		    description
		       "Collector IP address type.";
                }

                leaf ipaddress {
                    type inet:ip-address;

		    description
		       "Collector IP address.";
                }

                leaf port {
                    type inet:port-number;

		    description
		       "Collector UDP port number.";
                }
            }
        }
    }
}
