module sonic-vlan-interface {
    namespace "http://github.com/Azure/sonic-vlan-interface";
    prefix sVlanIf;

    import ietf-inet-types {
        prefix inet;
    }

    import sonic-vlan {
        prefix svlan;
    }

    import sonic-vrf {
        prefix vrf;
    }

    import sonic-common {
        prefix cmn;
    }

    import sonic-interface-common {
        prefix sonic-if-cmn;
    }

    organization
        "SONiC";

    contact
        "SONiC";

    description
        "SONIC VLAN INTERFACE";

    revision 2020-04-07 {
        description
            "Add VRF and IP address attribute";
    }
    revision 2020-02-28 {
        description
            "Add DHCP server attribute";
    }
    revision 2020-02-15 {
        description
            "Add ipv6_use_link_local_only attribute to interface object.";
    }
    revision 2019-12-01 {
        description
            "Add vrf_name for VRF interface binding.";
    }
    revision 2019-07-02 {
        description
            "Initial revision.";
    }


    container sonic-vlan-interface {

        container VLAN_INTERFACE {

			list VLAN_INTERFACE_LIST {
				key "vlanName";

				leaf vlanName{
					type leafref {
						path "/svlan:sonic-vlan/svlan:VLAN/svlan:VLAN_LIST/svlan:name";
					}
				}

				leaf nat_zone {
					type uint8 {
						range "0..3";
					}
				}

				leaf vrf_name {
					type leafref {
						path "/vrf:sonic-vrf/vrf:VRF/vrf:VRF_LIST/vrf:vrf_name";
					}
				} 

				leaf-list dhcp_servers{
					max-elements 4;
					type inet:ip-address;
					must "((/cmn:operation/cmn:operation != 'CREATE') and (/cmn:operation/cmn:operation != 'UPDATE')) or " +
						"(count(/sonic-vlan-interface/VLAN_INTERFACE/VLAN_INTERFACE_IPADDR_LIST[vlanName=current()/../vlanName]) > 1)"
						{
							error-message "DHCP server can be configured on vlan routing interface only";
							error-app-tag dhcp-server-invalid-vlan-routing-interface;
						}
				}

				leaf-list dhcpv6_servers{
					max-elements 4;
					type inet:ipv6-address;
					must "((/cmn:operation/cmn:operation != 'CREATE') and (/cmn:operation/cmn:operation != 'UPDATE')) or " +
						"(count(/sonic-vlan-interface/VLAN_INTERFACE/VLAN_INTERFACE_IPADDR_LIST[vlanName=current()/../vlanName]) > 1)"
						{
							error-message "DHCP server can be configured on vlan routing interface only";
							error-app-tag dhcp-server-invalid-vlan-routing-interface;
						}
				}

				leaf ipv6_use_link_local_only {
					type cmn:mode-enable;
					default disable;
					description
						"Enable IPv6 link local address on interface";
				}

				leaf-list helper_address {
					type sonic-if-cmn:vrf-ip;
					description
						"List of destination addresses with each being a combination of Vrf and IP address";
				}
			}

			list VLAN_INTERFACE_IPADDR_LIST {
				key "vlanName ip_prefix";

				leaf vlanName{
					type leafref {
						path "/svlan:sonic-vlan/svlan:VLAN/svlan:VLAN_LIST/svlan:name";
					}
				}

				leaf ip_prefix {
					type inet:ip-prefix;

				}
			}
		}
	}
}
