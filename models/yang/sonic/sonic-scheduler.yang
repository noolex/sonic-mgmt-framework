module sonic-scheduler {
    namespace "http://github.com/Azure/sonic-scheduler";
    prefix sch;

    organization
        "SONiC";

    contact
        "SONiC";

    description
        "SONIC SCHEDULER";

    revision 2019-05-15 {
        description
            "Initial revision.";
    }

    container sonic-scheduler {

        container SCHEDULER {

            list SCHEDULER_LIST {
                key "name";

                leaf name{
                    type string;
                }

                leaf type {
                    type enumeration {
                        enum DWRR;
                        enum WRR;
                        enum PRIORITY;
                    }
                }

                leaf weight {
                    type uint8 {
                        range "0..255";
                    }
                }

                leaf priority {
                    type uint8 {
                        range "0..9";
                    }
                }

                leaf cir {
                  type uint64;
                  units bps;
                  description
                        "Committed information rate for the dual-rate token
                        bucket policer.  This value represents the rate at which
                        tokens are added to the primary bucket.";
                }

                leaf pir {
                  type uint64;
                  units bps;
                  description
                        "Peak information rate for the dual-rate token bucket
                        policer.  This value represents the rate at which tokens
                        are added to the secondary bucket.";
                }

                leaf bc {
                  type uint32;
                  units bytes;
                  description
                        "Committed burst size for the dual-rate token bucket
                        policer.  This value represents the depth of the token
                        bucket.";
                }

                leaf be {
                  type uint32;
                  units bytes;
                  description
                        "Excess burst size for the dual-rate token bucket policer.
                        This value represents the depth of the secondary bucket.";
                }

            }
        }
    }
}
