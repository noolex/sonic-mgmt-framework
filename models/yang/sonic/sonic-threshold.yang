module sonic-threshold {
    namespace "http://github.com/Azure/sonic-threshold";
    prefix threshold;
    yang-version 1.1;

    import sonic-port {
        prefix prt;
    }

    import sonic-extension {
        prefix sonic-ext;
    }

    organization
        "SONiC";

    contact
        "SONiC";

    description
        "This module allows configuration of a threshold on supported buffers.
	The feature tracks ingress and egress buffer threshold breaches and notify
	network congestion event in real-time.";

    revision 2020-04-21 {
        description
            "Initial revision.";

    }

    container sonic-threshold {

	container THRESHOLD_TABLE {

	     description
		"Configuration of a threshold on supported buffers in ingress and egress.";

	     list THRESHOLD_TABLE_LIST {
		key "buffer threshold_buffer_type interface_name buffer_index_per_port";

		 leaf buffer {
	              type enumeration {
				enum priority-group;
				enum queue;
			}

			description
			   "Configure buffer Threshold type as priority-group/queue.";
		}

		leaf threshold_buffer_type {
                        type enumeration {
                           enum shared;
                           enum headroom;
		           enum unicast;
			   enum multicast;
                        }

			description
			   "Priority group/queue threshold buffer types.";
                 }

		 leaf interface_name {
		      type union {
				type leafref {
					path "/prt:sonic-port/prt:PORT/prt:PORT_LIST/prt:ifname";
				}
				type string {
                                        pattern "CPU";
                                }
			}

			description
			   "Name of the interface for which priority-group/queue thresholds can be configured.";
		 }

		 leaf buffer_index_per_port {
			type uint8 {
		           range "0..7" {
				error-message "buffer index per port must be in range 0-7.";
			   }
			}

			description
			   "Priority group/queue index value.";
	         }

	         leaf threshold {
			type uint8 {
                           range "1..100" {
				error-message "threshold value must be in range 1-100.";
			   }
			}

			description
			   "Threshold value for a specific buffer of an interface.";
	         }
		}
	}
	container THRESHOLD_BREACH_TABLE {
	    sonic-ext:db-name "COUNTERS_DB";
            sonic-ext:key-delim ":";

            config false;
            description "config db threshold breach table";

	    list THRESHOLD_BREACH_TABLE_LIST {
		key "breachreport eventid";

		leaf breachreport {
                      type enumeration {
                                enum breach-report;
                        }

                        description
                           "Breach report event";
                }

		leaf eventid {
			type uint8 {
                           range "0..7" {
                                error-message "Invalid breach-report index it must be in range 0-7.";
                           }
                        }

                        description
                           "Breach report event id.";
		}

		leaf buffer {
                      type enumeration {
                                enum priority-group;
                                enum queue;
                        }

                        description
                           "Buffer - priority-group or queue";
                }

		leaf type {
                        type enumeration {
                           enum shared;
                           enum headroom;
                           enum unicast;
                           enum multicast;
                        }

                        description
                           "Priority group/queue threshold buffer types.";
                 }

		 leaf port {
		      type union {
				type leafref {
					path "/prt:sonic-port/prt:PORT/prt:PORT_LIST/prt:ifname";
				}
				type string {
                                        pattern "CPU";
                                }
			}

			description
			   "Name of the interface for which priority-group/queue thresholds can be configured.";
		 }

		 leaf index {
			type uint8 {
		           range "0..7" {
				error-message "buffer index per port must be in range 0-7.";
			   }
			}

			description
			   "Priority group/queue index value.";
	         }

	         leaf breach_value {
			type uint8 {
                           range "1..100" {
				error-message "breach value must be in range 1-100.";
			   }
			}

			description
			   "Counter value in % at breach.";
		}

		leaf SAI_QUEUE_STAT_SHARED_WATERMARK_BYTES {
			type int64;

			description
			    "SAI queue stat counter value in bytes at breach.";
		}

		leaf SAI_INGRESS_PRIORITY_GROUP_STAT_SHARED_WATERMARK_BYTES {
			type int64;

			description
			    "SAI ingress priority-group stat shared watermark in bytes at breach.";
		}

		leaf SAI_INGRESS_PRIORITY_GROUP_STAT_XOFF_ROOM_WATERMARK_BYTES {
			type int64;

			description
			    "SAI ingress priority-greoup stat xoff watermark counter value in bytes at breach.";
		}

		leaf time-stamp {
			type string {
				pattern '\d{4}-\d{2}-\d{2}T\d{2}:\d{2}:\d{2}(\.\d+)?'
					+ '(Z|[\+\-]\d{2}:\d{2})';
			}

			description
			    "time-stamp of the event when the threshold breach occurred.";
		}
	    }
        }
    }
}
