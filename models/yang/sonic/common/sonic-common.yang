module sonic-common {
    namespace "http://github.com/Azure/sonic-common";
    prefix scommon;

    organization
        "SONiC";

    contact
        "SONiC";

    description
        "SONIC Common";

    revision 2019-05-15 {
        description
            "Initial revision.";
    }

    typedef tagging_mode {
        type enumeration {
            enum untagged;
            enum tagged;
            enum priority_tagged;
        }
    }

    typedef admin-status {
        type enumeration {
            enum up;
            enum down;
        }
    }

    typedef oper-status {
        type enumeration {
            enum up;
            enum down;
        }
    }

    typedef mode-enable {
          type enumeration {
              enum enable;
              enum disable;
          }
      }

    container operation {
	    leaf operation {
		    type enumeration {
			    enum CREATE;
			    enum UPDATE;
			    enum DELETE;
		    }
	    }
    }
}
