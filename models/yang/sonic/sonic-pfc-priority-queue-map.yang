module sonic-pfc-priority-queue-map {
	namespace "http://github.com/Azure/sonic-pfc-priority-queue-map";
	prefix ppq;

	import sonic-extension {
		prefix sonic-ext;
	}

	organization
		"SONiC";

	contact
		"SONiC";

	description
		"SONIC MAP_PFC_PRIORITY_TO_QUEUE";

	revision 2019-05-15 {
		description
			"Initial revision.";
	}

	container sonic-pfc-priority-queue-map {	

		container MAP_PFC_PRIORITY_TO_QUEUE {

			list MAP_PFC_PRIORITY_TO_QUEUE_LIST {
				key "name";
				sonic-ext:map-list true; //special conversion for map tables
				sonic-ext:map-leaf "pfc_priority qindex"; //every key:value pair is mapped to list keys, e.g. "1":"7" ==> pfc_priority=1, qindex=7

				leaf name {
					type string;
				}

				list MAP_PFC_PRIORITY_TO_QUEUE { //this is list inside list for storing mapping between two fields
					key "pfc_priority qindex";

					leaf pfc_priority {
						type string {
							pattern "[0-9]?";
						}
					}

					leaf qindex {
						type string {
							pattern "[0-9]?";
						}
					}
				}

			}
		}
	}
}
