module openconfig-relay-agent-annot {

    yang-version "1";

    namespace "http://openconfig.net/yang/annotation/oc-relay-annot";
    prefix "oc-relay-annot";

    import openconfig-relay-agent { prefix oc-relay; }
    import sonic-extensions { prefix sonic-ext; }


    deviation /oc-relay:relay-agent {
      deviate add {
      }
    }

    deviation /oc-relay:relay-agent/oc-relay:dhcp {
      deviate add {
      }
    }

    deviation /oc-relay:relay-agent/oc-relay:dhcp/oc-relay:config {
      deviate add {
      }
    }

    deviation /oc-relay:relay-agent/oc-relay:dhcp/oc-relay:config/oc-relay:enable-relay-agent {
      deviate add {
      }
    }

    deviation /oc-relay:relay-agent/oc-relay:dhcp/oc-relay:state {
      deviate add {
      }
    }

    deviation /oc-relay:relay-agent/oc-relay:dhcp/oc-relay:state/oc-relay:enable-relay-agent {
      deviate add {
      }
    }

    deviation /oc-relay:relay-agent/oc-relay:dhcp/oc-relay:agent-information-option {
      deviate add {
      }
    }

    deviation /oc-relay:relay-agent/oc-relay:dhcp/oc-relay:agent-information-option/oc-relay:config {
      deviate add {
      }
    }

    deviation /oc-relay:relay-agent/oc-relay:dhcp/oc-relay:agent-information-option/oc-relay:config/oc-relay:enable {
      deviate add {
      }
    }

    deviation /oc-relay:relay-agent/oc-relay:dhcp/oc-relay:agent-information-option/oc-relay:state {
      deviate add {
      }
    }

    deviation /oc-relay:relay-agent/oc-relay:dhcp/oc-relay:agent-information-option/oc-relay:state/oc-relay:enable {
      deviate add {
      }
    }

    deviation /oc-relay:relay-agent/oc-relay:dhcp/oc-relay:interfaces {
      deviate add {
      }
    }

    deviation /oc-relay:relay-agent/oc-relay:dhcp/oc-relay:interfaces/oc-relay:interface {
      deviate add {
         sonic-ext:table-transformer "relay_agent_table_xfmr";
         sonic-ext:key-transformer "relay_agent_intf_tbl_key_xfmr";

      }
    }

    deviation /oc-relay:relay-agent/oc-relay:dhcp/oc-relay:interfaces/oc-relay:interface/oc-relay:state {
      deviate add {
      }
    }

    deviation /oc-relay:relay-agent/oc-relay:dhcp/oc-relay:interfaces/oc-relay:interface/oc-relay:state/oc-relay:enable {
      deviate add {
      }
    }

    deviation /oc-relay:relay-agent/oc-relay:dhcp/oc-relay:interfaces/oc-relay:interface/oc-relay:state/oc-relay:helper-address {
      deviate add {
      }
    }

    deviation /oc-relay:relay-agent/oc-relay:dhcp/oc-relay:interfaces/oc-relay:interface/oc-relay:state/oc-relay:id {
      deviate add {
      }
    }

    deviation /oc-relay:relay-agent/oc-relay:dhcp/oc-relay:interfaces/oc-relay:interface/oc-relay:state/oc-relay:counters {
      deviate add {
      }
    }

    deviation /oc-relay:relay-agent/oc-relay:dhcp/oc-relay:interfaces/oc-relay:interface/oc-relay:state/oc-relay:counters/oc-relay:bootreply-sent {
      deviate add {
      }
    }

    deviation /oc-relay:relay-agent/oc-relay:dhcp/oc-relay:interfaces/oc-relay:interface/oc-relay:state/oc-relay:counters/oc-relay:dhcp-ack-sent {
      deviate add {
      }
    }

    deviation /oc-relay:relay-agent/oc-relay:dhcp/oc-relay:interfaces/oc-relay:interface/oc-relay:state/oc-relay:counters/oc-relay:total-dropped {
      deviate add {
      }
    }

    deviation /oc-relay:relay-agent/oc-relay:dhcp/oc-relay:interfaces/oc-relay:interface/oc-relay:state/oc-relay:counters/oc-relay:dhcp-nack-sent {
      deviate add {
      }
    }

    deviation /oc-relay:relay-agent/oc-relay:dhcp/oc-relay:interfaces/oc-relay:interface/oc-relay:state/oc-relay:counters/oc-relay:dhcp-decline-received {
      deviate add {
      }
    }

    deviation /oc-relay:relay-agent/oc-relay:dhcp/oc-relay:interfaces/oc-relay:interface/oc-relay:state/oc-relay:counters/oc-relay:dhcp-inform-received {
      deviate add {
      }
    }

    deviation /oc-relay:relay-agent/oc-relay:dhcp/oc-relay:interfaces/oc-relay:interface/oc-relay:state/oc-relay:counters/oc-relay:bootrequest-received {
      deviate add {
      }
    }

    deviation /oc-relay:relay-agent/oc-relay:dhcp/oc-relay:interfaces/oc-relay:interface/oc-relay:state/oc-relay:counters/oc-relay:invalid-opcode {
      deviate add {
      }
    }

    deviation /oc-relay:relay-agent/oc-relay:dhcp/oc-relay:interfaces/oc-relay:interface/oc-relay:state/oc-relay:counters/oc-relay:bootrequest-sent {
      deviate add {
      }
    }

    deviation /oc-relay:relay-agent/oc-relay:dhcp/oc-relay:interfaces/oc-relay:interface/oc-relay:state/oc-relay:counters/oc-relay:dhcp-offer-sent {
      deviate add {
      }
    }

    deviation /oc-relay:relay-agent/oc-relay:dhcp/oc-relay:interfaces/oc-relay:interface/oc-relay:state/oc-relay:counters/oc-relay:dhcp-discover-received {
      deviate add {
      }
    }

    deviation /oc-relay:relay-agent/oc-relay:dhcp/oc-relay:interfaces/oc-relay:interface/oc-relay:state/oc-relay:counters/oc-relay:dhcp-release-received {
      deviate add {
      }
    }

    deviation /oc-relay:relay-agent/oc-relay:dhcp/oc-relay:interfaces/oc-relay:interface/oc-relay:state/oc-relay:counters/oc-relay:invalid-options {
      deviate add {
      }
    }

    deviation /oc-relay:relay-agent/oc-relay:dhcp/oc-relay:interfaces/oc-relay:interface/oc-relay:state/oc-relay:counters/oc-relay:dhcp-request-received {
      deviate add {
      }
    }

    deviation /oc-relay:relay-agent/oc-relay:dhcp/oc-relay:interfaces/oc-relay:interface/oc-relay:interface-ref {
      deviate add {
      }
    }

    deviation /oc-relay:relay-agent/oc-relay:dhcp/oc-relay:interfaces/oc-relay:interface/oc-relay:interface-ref/oc-relay:state {
      deviate add {
      }
    }

    deviation /oc-relay:relay-agent/oc-relay:dhcp/oc-relay:interfaces/oc-relay:interface/oc-relay:interface-ref/oc-relay:state/oc-relay:subinterface {
      deviate add {
      }
    }

    deviation /oc-relay:relay-agent/oc-relay:dhcp/oc-relay:interfaces/oc-relay:interface/oc-relay:interface-ref/oc-relay:state/oc-relay:interface {
      deviate add {
      }
    }

    deviation /oc-relay:relay-agent/oc-relay:dhcp/oc-relay:interfaces/oc-relay:interface/oc-relay:interface-ref/oc-relay:config {
      deviate add {
      }
    }

    deviation /oc-relay:relay-agent/oc-relay:dhcp/oc-relay:interfaces/oc-relay:interface/oc-relay:interface-ref/oc-relay:config/oc-relay:subinterface {
      deviate add {
      }
    }

    deviation /oc-relay:relay-agent/oc-relay:dhcp/oc-relay:interfaces/oc-relay:interface/oc-relay:interface-ref/oc-relay:config/oc-relay:interface {
      deviate add {
      }
    }

    deviation /oc-relay:relay-agent/oc-relay:dhcp/oc-relay:interfaces/oc-relay:interface/oc-relay:agent-information-option {
      deviate add {
      }
    }

    deviation /oc-relay:relay-agent/oc-relay:dhcp/oc-relay:interfaces/oc-relay:interface/oc-relay:agent-information-option/oc-relay:config {
      deviate add {
      }
    }

    deviation /oc-relay:relay-agent/oc-relay:dhcp/oc-relay:interfaces/oc-relay:interface/oc-relay:agent-information-option/oc-relay:config/oc-relay:enable {
      deviate add {
      }
    }

    deviation /oc-relay:relay-agent/oc-relay:dhcp/oc-relay:interfaces/oc-relay:interface/oc-relay:agent-information-option/oc-relay:config/oc-relay:circuit-id {
      deviate add {
      }
    }

    deviation /oc-relay:relay-agent/oc-relay:dhcp/oc-relay:interfaces/oc-relay:interface/oc-relay:agent-information-option/oc-relay:config/oc-relay:remote-id {
      deviate add {
      }
    }

    deviation /oc-relay:relay-agent/oc-relay:dhcp/oc-relay:interfaces/oc-relay:interface/oc-relay:agent-information-option/oc-relay:state {
      deviate add {
      }
    }

    deviation /oc-relay:relay-agent/oc-relay:dhcp/oc-relay:interfaces/oc-relay:interface/oc-relay:agent-information-option/oc-relay:state/oc-relay:sent-circuit-id {
      deviate add {
      }
    }

    deviation /oc-relay:relay-agent/oc-relay:dhcp/oc-relay:interfaces/oc-relay:interface/oc-relay:agent-information-option/oc-relay:state/oc-relay:sent-remote-id {
      deviate add {
      }
    }

    deviation /oc-relay:relay-agent/oc-relay:dhcp/oc-relay:interfaces/oc-relay:interface/oc-relay:agent-information-option/oc-relay:state/oc-relay:enable {
      deviate add {
      }
    }

    deviation /oc-relay:relay-agent/oc-relay:dhcp/oc-relay:interfaces/oc-relay:interface/oc-relay:agent-information-option/oc-relay:state/oc-relay:circuit-id {
      deviate add {
      }
    }

    deviation /oc-relay:relay-agent/oc-relay:dhcp/oc-relay:interfaces/oc-relay:interface/oc-relay:agent-information-option/oc-relay:state/oc-relay:remote-id {
      deviate add {
      }
    }

    deviation /oc-relay:relay-agent/oc-relay:dhcp/oc-relay:interfaces/oc-relay:interface/oc-relay:id {
      deviate add {
      }
    }

    deviation /oc-relay:relay-agent/oc-relay:dhcp/oc-relay:interfaces/oc-relay:interface/oc-relay:config {
      deviate add {
      }
    }

    deviation /oc-relay:relay-agent/oc-relay:dhcp/oc-relay:interfaces/oc-relay:interface/oc-relay:config/oc-relay:id {
      deviate add {         
      }
    }

    deviation /oc-relay:relay-agent/oc-relay:dhcp/oc-relay:interfaces/oc-relay:interface/oc-relay:config/oc-relay:enable {
      deviate add {
      }
    }

    deviation /oc-relay:relay-agent/oc-relay:dhcp/oc-relay:interfaces/oc-relay:interface/oc-relay:config/oc-relay:helper-address {
      deviate add {
         sonic-ext:field-name "dhcp_servers";
      }
    }

    deviation /oc-relay:relay-agent/oc-relay:dhcpv6 {
      deviate add {
      }
    }

    deviation /oc-relay:relay-agent/oc-relay:dhcpv6/oc-relay:config {
      deviate add {
      }
    }

    deviation /oc-relay:relay-agent/oc-relay:dhcpv6/oc-relay:config/oc-relay:enable-relay-agent {
      deviate add {
      }
    }

    deviation /oc-relay:relay-agent/oc-relay:dhcpv6/oc-relay:state {
      deviate add {
      }
    }

    deviation /oc-relay:relay-agent/oc-relay:dhcpv6/oc-relay:state/oc-relay:enable-relay-agent {
      deviate add {
      }
    }

    deviation /oc-relay:relay-agent/oc-relay:dhcpv6/oc-relay:options {
      deviate add {
      }
    }

    deviation /oc-relay:relay-agent/oc-relay:dhcpv6/oc-relay:options/oc-relay:config {
      deviate add {
      }
    }

    deviation /oc-relay:relay-agent/oc-relay:dhcpv6/oc-relay:options/oc-relay:config/oc-relay:enable-remote-id {
      deviate add {
      }
    }

    deviation /oc-relay:relay-agent/oc-relay:dhcpv6/oc-relay:options/oc-relay:config/oc-relay:enable-interface-id {
      deviate add {
      }
    }

    deviation /oc-relay:relay-agent/oc-relay:dhcpv6/oc-relay:options/oc-relay:state {
      deviate add {
      }
    }

    deviation /oc-relay:relay-agent/oc-relay:dhcpv6/oc-relay:options/oc-relay:state/oc-relay:enable-interface-id {
      deviate add {
      }
    }

    deviation /oc-relay:relay-agent/oc-relay:dhcpv6/oc-relay:options/oc-relay:state/oc-relay:enable-remote-id {
      deviate add {
      }
    }

    deviation /oc-relay:relay-agent/oc-relay:dhcpv6/oc-relay:interfaces {
      deviate add {
      }
    }

    deviation /oc-relay:relay-agent/oc-relay:dhcpv6/oc-relay:interfaces/oc-relay:interface {
      deviate add {
         sonic-ext:table-transformer "relay_agent_table_xfmr";
         sonic-ext:key-transformer "relay_agent_intf_tbl_key_xfmr";
      }
    }

    deviation /oc-relay:relay-agent/oc-relay:dhcpv6/oc-relay:interfaces/oc-relay:interface/oc-relay:state {
      deviate add {
      }
    }

    deviation /oc-relay:relay-agent/oc-relay:dhcpv6/oc-relay:interfaces/oc-relay:interface/oc-relay:state/oc-relay:id {
      deviate add {
      }
    }

    deviation /oc-relay:relay-agent/oc-relay:dhcpv6/oc-relay:interfaces/oc-relay:interface/oc-relay:state/oc-relay:enable {
      deviate add {
      }
    }

    deviation /oc-relay:relay-agent/oc-relay:dhcpv6/oc-relay:interfaces/oc-relay:interface/oc-relay:state/oc-relay:counters {
      deviate add {
      }
    }

    deviation /oc-relay:relay-agent/oc-relay:dhcpv6/oc-relay:interfaces/oc-relay:interface/oc-relay:state/oc-relay:counters/oc-relay:dhcpv6-adverstise-sent {
      deviate add {
      }
    }

    deviation /oc-relay:relay-agent/oc-relay:dhcpv6/oc-relay:interfaces/oc-relay:interface/oc-relay:state/oc-relay:counters/oc-relay:dhcpv6-rebind-received {
      deviate add {
      }
    }

    deviation /oc-relay:relay-agent/oc-relay:dhcpv6/oc-relay:interfaces/oc-relay:interface/oc-relay:state/oc-relay:counters/oc-relay:dhcpv6-release-received {
      deviate add {
      }
    }

    deviation /oc-relay:relay-agent/oc-relay:dhcpv6/oc-relay:interfaces/oc-relay:interface/oc-relay:state/oc-relay:counters/oc-relay:dhcpv6-solicit-received {
      deviate add {
      }
    }

    deviation /oc-relay:relay-agent/oc-relay:dhcpv6/oc-relay:interfaces/oc-relay:interface/oc-relay:state/oc-relay:counters/oc-relay:dhcpv6-confirm-received {
      deviate add {
      }
    }

    deviation /oc-relay:relay-agent/oc-relay:dhcpv6/oc-relay:interfaces/oc-relay:interface/oc-relay:state/oc-relay:counters/oc-relay:dhcpv6-decline-received {
      deviate add {
      }
    }

    deviation /oc-relay:relay-agent/oc-relay:dhcpv6/oc-relay:interfaces/oc-relay:interface/oc-relay:state/oc-relay:counters/oc-relay:dhcpv6-reconfigure-sent {
      deviate add {
      }
    }

    deviation /oc-relay:relay-agent/oc-relay:dhcpv6/oc-relay:interfaces/oc-relay:interface/oc-relay:state/oc-relay:counters/oc-relay:dhcpv6-relay-forw-sent {
      deviate add {
      }
    }

    deviation /oc-relay:relay-agent/oc-relay:dhcpv6/oc-relay:interfaces/oc-relay:interface/oc-relay:state/oc-relay:counters/oc-relay:invalid-opcode {
      deviate add {
      }
    }

    deviation /oc-relay:relay-agent/oc-relay:dhcpv6/oc-relay:interfaces/oc-relay:interface/oc-relay:state/oc-relay:counters/oc-relay:dhcpv6-info-request-received {
      deviate add {
      }
    }

    deviation /oc-relay:relay-agent/oc-relay:dhcpv6/oc-relay:interfaces/oc-relay:interface/oc-relay:state/oc-relay:counters/oc-relay:total-dropped {
      deviate add {
      }
    }

    deviation /oc-relay:relay-agent/oc-relay:dhcpv6/oc-relay:interfaces/oc-relay:interface/oc-relay:state/oc-relay:counters/oc-relay:dhcpv6-request-received {
      deviate add {
      }
    }

    deviation /oc-relay:relay-agent/oc-relay:dhcpv6/oc-relay:interfaces/oc-relay:interface/oc-relay:state/oc-relay:counters/oc-relay:dhcpv6-relay-reply-received {
      deviate add {
      }
    }

    deviation /oc-relay:relay-agent/oc-relay:dhcpv6/oc-relay:interfaces/oc-relay:interface/oc-relay:state/oc-relay:counters/oc-relay:dhcpv6-reply-sent {
      deviate add {
      }
    }

    deviation /oc-relay:relay-agent/oc-relay:dhcpv6/oc-relay:interfaces/oc-relay:interface/oc-relay:state/oc-relay:counters/oc-relay:invalid-options {
      deviate add {
      }
    }

    deviation /oc-relay:relay-agent/oc-relay:dhcpv6/oc-relay:interfaces/oc-relay:interface/oc-relay:state/oc-relay:helper-address {
      deviate add {
      }
    }

    deviation /oc-relay:relay-agent/oc-relay:dhcpv6/oc-relay:interfaces/oc-relay:interface/oc-relay:interface-ref {
      deviate add {
      }
    }

    deviation /oc-relay:relay-agent/oc-relay:dhcpv6/oc-relay:interfaces/oc-relay:interface/oc-relay:interface-ref/oc-relay:state {
      deviate add {
      }
    }

    deviation /oc-relay:relay-agent/oc-relay:dhcpv6/oc-relay:interfaces/oc-relay:interface/oc-relay:interface-ref/oc-relay:state/oc-relay:interface {
      deviate add {
      }
    }

    deviation /oc-relay:relay-agent/oc-relay:dhcpv6/oc-relay:interfaces/oc-relay:interface/oc-relay:interface-ref/oc-relay:state/oc-relay:subinterface {
      deviate add {
      }
    }

    deviation /oc-relay:relay-agent/oc-relay:dhcpv6/oc-relay:interfaces/oc-relay:interface/oc-relay:interface-ref/oc-relay:config {
      deviate add {
      }
    }

    deviation /oc-relay:relay-agent/oc-relay:dhcpv6/oc-relay:interfaces/oc-relay:interface/oc-relay:interface-ref/oc-relay:config/oc-relay:subinterface {
      deviate add {
      }
    }

    deviation /oc-relay:relay-agent/oc-relay:dhcpv6/oc-relay:interfaces/oc-relay:interface/oc-relay:interface-ref/oc-relay:config/oc-relay:interface {
      deviate add {
      }
    }

    deviation /oc-relay:relay-agent/oc-relay:dhcpv6/oc-relay:interfaces/oc-relay:interface/oc-relay:options {
      deviate add {
      }
    }

    deviation /oc-relay:relay-agent/oc-relay:dhcpv6/oc-relay:interfaces/oc-relay:interface/oc-relay:options/oc-relay:config {
      deviate add {
      }
    }

    deviation /oc-relay:relay-agent/oc-relay:dhcpv6/oc-relay:interfaces/oc-relay:interface/oc-relay:options/oc-relay:config/oc-relay:enable-interface-id {
      deviate add {
      }
    }

    deviation /oc-relay:relay-agent/oc-relay:dhcpv6/oc-relay:interfaces/oc-relay:interface/oc-relay:options/oc-relay:config/oc-relay:enable-remote-id {
      deviate add {
      }
    }

    deviation /oc-relay:relay-agent/oc-relay:dhcpv6/oc-relay:interfaces/oc-relay:interface/oc-relay:options/oc-relay:config/oc-relay:interface-id {
      deviate add {
      }
    }

    deviation /oc-relay:relay-agent/oc-relay:dhcpv6/oc-relay:interfaces/oc-relay:interface/oc-relay:options/oc-relay:config/oc-relay:remote-id {
      deviate add {
      }
    }

    deviation /oc-relay:relay-agent/oc-relay:dhcpv6/oc-relay:interfaces/oc-relay:interface/oc-relay:options/oc-relay:state {
      deviate add {
      }
    }

    deviation /oc-relay:relay-agent/oc-relay:dhcpv6/oc-relay:interfaces/oc-relay:interface/oc-relay:options/oc-relay:state/oc-relay:sent-remote-id {
      deviate add {
      }
    }

    deviation /oc-relay:relay-agent/oc-relay:dhcpv6/oc-relay:interfaces/oc-relay:interface/oc-relay:options/oc-relay:state/oc-relay:enable-interface-id {
      deviate add {
      }
    }

    deviation /oc-relay:relay-agent/oc-relay:dhcpv6/oc-relay:interfaces/oc-relay:interface/oc-relay:options/oc-relay:state/oc-relay:enable-remote-id {
      deviate add {
      }
    }

    deviation /oc-relay:relay-agent/oc-relay:dhcpv6/oc-relay:interfaces/oc-relay:interface/oc-relay:options/oc-relay:state/oc-relay:interface-id {
      deviate add {
      }
    }

    deviation /oc-relay:relay-agent/oc-relay:dhcpv6/oc-relay:interfaces/oc-relay:interface/oc-relay:options/oc-relay:state/oc-relay:remote-id {
      deviate add {
      }
    }

    deviation /oc-relay:relay-agent/oc-relay:dhcpv6/oc-relay:interfaces/oc-relay:interface/oc-relay:options/oc-relay:state/oc-relay:sent-interface-id {
      deviate add {
      }
    }

    deviation /oc-relay:relay-agent/oc-relay:dhcpv6/oc-relay:interfaces/oc-relay:interface/oc-relay:id {
      deviate add {
      }
    }

    deviation /oc-relay:relay-agent/oc-relay:dhcpv6/oc-relay:interfaces/oc-relay:interface/oc-relay:config {
      deviate add {
      }
    }

    deviation /oc-relay:relay-agent/oc-relay:dhcpv6/oc-relay:interfaces/oc-relay:interface/oc-relay:config/oc-relay:id {
      deviate add {
      }
    }

    deviation /oc-relay:relay-agent/oc-relay:dhcpv6/oc-relay:interfaces/oc-relay:interface/oc-relay:config/oc-relay:enable {
      deviate add {
      }
    }

    deviation /oc-relay:relay-agent/oc-relay:dhcpv6/oc-relay:interfaces/oc-relay:interface/oc-relay:config/oc-relay:helper-address {
      deviate add {
         sonic-ext:field-name "dhcpv6_servers";
      }
    }

}
