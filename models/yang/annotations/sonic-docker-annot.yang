module sonic-docker-annot {

    yang-version "1.1";

    namespace "http://openconfig.net/yang/annotation/sdocker-annot";
    prefix "sdocker-annot";

    import sonic-docker { prefix sdocker; }
    import sonic-extensions { prefix sonic-ext; }

    deviation /sdocker:docker-exec {
        deviate add {
            sonic-ext:rpc-callback "rpc_docker_exec";
        }
    }
}
