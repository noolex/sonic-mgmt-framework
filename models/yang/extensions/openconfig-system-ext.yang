module openconfig-system-ext {

    yang-version "1";

    namespace "http://openconfig.net/yang/system/extension";

    prefix "oc-sys-ext";

    import openconfig-system { prefix oc-sys; }
    import openconfig-inet-types { prefix inet; }

    // meta
    organization "OpenConfig working group";

    contact
        "OpenConfig working group
        netopenconfig@googlegroups.com";

    description
        "Model for managing TACACS+ configurations .";

    revision 2020-03-30 {
        description
            "Added NAS-IP|IPV6-Address attribute for RADIUS.";
    }

    revision 2019-11-05 {
        description
            "Initial augment file.";
    }

    // augment statements

    augment "/oc-sys:system/oc-sys:aaa/oc-sys:authentication/oc-sys:config" {
        leaf failthrough {
            type boolean;
            description "Indicating whether authentication failthrough should be enabled/disabled";
        }
    }

    augment "/oc-sys:system/oc-sys:aaa/oc-sys:server-groups/oc-sys:server-group/oc-sys:servers/oc-sys:server/oc-sys:config" {
        leaf  auth-type {
            type string;
            description "The server authentication type pap/chap/mschap/mschapv2";
        }
        leaf  priority {
            type uint16;
            description "The server priority";
        }
        leaf vrf {
            type string;
            description "The server's VRF";
        }
    }

    augment "/oc-sys:system/oc-sys:aaa/oc-sys:server-groups/oc-sys:server-group/oc-sys:config" {
        leaf  source-address {
            type inet:ip-address;
            description "The global source ip";
        }
        leaf  nas-ip-address {
            type inet:ip-address;
            description "The global nas ip|ipv6 address attribute";
        }
        leaf  auth-type {
            type string;
            description "The global authentication type pap/chap/mschap/mschapv2";
        }
        leaf  secret-key {
            type string;
            description "The global authentication passkey";
        }
        leaf  timeout {
            type uint16;
            description "The global authentication timeout";
        }
        leaf retransmit-attempts {
          type uint8;
          description
              "Number of times the system may resend a request to the
              RADIUS server when it is unresponsive";
        }
    }

    grouping ssh-vrf-config {
      description
       "Configuration data for ssh server vrf";
        leaf vrf-name {
            type string {
                pattern "mgmt|Vrf[a-zA-Z0-9_-]+" {
                    error-message "Invalid VRF name for SSH server";
                    error-app-tag vrf-name-ssh-invalid;
                }
            }
            description
                "VRF name";
        }
        leaf port {
            default 22;
            type uint16;
            description
                "SSH port number";
        }
    }

    augment "/oc-sys:system/oc-sys:ssh-server" {
        container ssh-server-vrfs {
          description
           "Container for ssh server vrfs";
            list ssh-server-vrf {
                key "vrf-name";
                max-elements 15;
                description
                  "list of ssh server vrf";
            
                leaf vrf-name {
                    type leafref {
                        path "../config/vrf-name";
                    }
                }

                container config {
                    description
                      "Configuration data for ssh server vrf";
                    uses ssh-vrf-config;
                }
                container state {
                    config false;
                    description
                      "Operational state data for ssh server vrf";
                    uses ssh-vrf-config;
                }
            }
        }
    }

    deviation /oc-sys:system/oc-sys:config/oc-sys:domain-name {
       deviate not-supported;
    }

    deviation /oc-sys:system/oc-sys:config/oc-sys:login-banner {
        deviate not-supported;
    }

    deviation /oc-sys:system/oc-sys:config/oc-sys:motd-banner {
        deviate not-supported;
    }
	
	// ssh-server deviations.

    deviation /oc-sys:system/oc-sys:ssh-server/oc-sys:config {
       deviate not-supported;
    }
    deviation /oc-sys:system/oc-sys:ssh-server/oc-sys:state {
       deviate not-supported;
    }
}
