module openconfig-network-instance-ext {

  yang-version "1";

  // namespace
  namespace "http://openconfig.net/yang/network-instance/extension";

  prefix "oc-netinst-ext";
  
  import ietf-yang-types {
        prefix ietf;
    }  

  // import some basic types
  import openconfig-network-instance { prefix "oc-netinst"; }

  description
        "This module describes a YANG model for network instance
        configuration extensions.";

  revision "2019-10-29" {
    description
      "Add OpenConfig unsupported attributes.";
  }

  grouping oc-table-connection-ext-config {
      leaf metric {
          type uint32;
          description
              "Metric for redistributed routes";
      }
  }

  grouping global-sag-config {
	  leaf anycast-mac {
		  description
			  "Static Anycast Gateway MAC addresses";
		  type ietf:mac-address;
	  }
	  
      leaf ipv4-enable {
        type boolean;
		default true;
      }

      leaf ipv6-enable {
        type boolean;
		default true;
      }
  }

  grouping global-sag-top {
	  container global-sag {
		  container config {
			  uses global-sag-config;
		  }
		  container state {
			  config false;
			  uses global-sag-config;
		  }
	  }
  }	

  augment "/oc-netinst:network-instances/oc-netinst:network-instance" {
      description
          "Global Anycast Gateway";
      uses global-sag-top;	
  }
	
  augment /oc-netinst:network-instances/oc-netinst:network-instance/oc-netinst:table-connections/oc-netinst:table-connection/oc-netinst:config {
      uses oc-table-connection-ext-config;
  }
 
  augment /oc-netinst:network-instances/oc-netinst:network-instance/oc-netinst:table-connections/oc-netinst:table-connection/oc-netinst:state {
      uses oc-table-connection-ext-config;
  }

  deviation /oc-netinst:network-instances/oc-netinst:network-instance/oc-netinst:inter-instance-policies {
      deviate not-supported;
  }

  deviation /oc-netinst:network-instances/oc-netinst:network-instance/oc-netinst:route-limits {
      deviate not-supported;
  }
  
  deviation /oc-netinst:network-instances/oc-netinst:network-instance/oc-netinst:connection-points {
      deviate not-supported;
  }
  
  deviation /oc-netinst:network-instances/oc-netinst:network-instance/oc-netinst:mpls {
      deviate not-supported;
  }
  
  deviation /oc-netinst:network-instances/oc-netinst:network-instance/oc-netinst:segment-routing {
      deviate not-supported;
  }

  deviation /oc-netinst:network-instances/oc-netinst:network-instance/oc-netinst:policy-forwarding {
	  deviate not-supported;
  }

  deviation /oc-netinst:network-instances/oc-netinst:network-instance/oc-netinst:afts/oc-netinst:ipv4-unicast/oc-netinst:ipv4-entry/oc-netinst:state/oc-netinst:next-hop-group {
      deviate not-supported;
  }

  deviation /oc-netinst:network-instances/oc-netinst:network-instance/oc-netinst:afts/oc-netinst:ipv6-unicast/oc-netinst:ipv6-entry/oc-netinst:state/oc-netinst:next-hop-group {
      deviate not-supported;
  }

  deviation /oc-netinst:network-instances/oc-netinst:network-instance/oc-netinst:afts/oc-netinst:policy-forwarding {
      deviate not-supported;
  }

  deviation /oc-netinst:network-instances/oc-netinst:network-instance/oc-netinst:afts/oc-netinst:mpls {
      deviate not-supported;
  }

  deviation /oc-netinst:network-instances/oc-netinst:network-instance/oc-netinst:afts/oc-netinst:ethernet {
      deviate not-supported;
  }

  deviation /oc-netinst:network-instances/oc-netinst:network-instance/oc-netinst:afts/oc-netinst:next-hop-groups {
      deviate not-supported;
  }

  deviation /oc-netinst:network-instances/oc-netinst:network-instance/oc-netinst:afts/oc-netinst:next-hops {
      deviate not-supported;
  }

  deviation /oc-netinst:network-instances/oc-netinst:network-instance/oc-netinst:protocols/oc-netinst:protocol/oc-netinst:igmp {
      deviate not-supported;
  }

  deviation /oc-netinst:network-instances/oc-netinst:network-instance/oc-netinst:protocols/oc-netinst:protocol/oc-netinst:pim {
      deviate not-supported;
  }

  deviation /oc-netinst:network-instances/oc-netinst:network-instance/oc-netinst:protocols/oc-netinst:protocol/oc-netinst:isis {
      deviate not-supported;
  }

  deviation /oc-netinst:network-instances/oc-netinst:network-instance/oc-netinst:protocols/oc-netinst:protocol/oc-netinst:local-aggregates {
      deviate not-supported;
  }
  
}
