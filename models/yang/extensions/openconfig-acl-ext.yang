module openconfig-acl-ext {

    yang-version "1";

    namespace "http://openconfig.net/yang/acl/extention";

    prefix "oc-acl-ext";

    import openconfig-packet-match-types { prefix oc-pkt-match-types; }
    import openconfig-acl { prefix oc-acl; }

    description
        "This model describes the acl extensions.";

    revision 2020-02-08 {
        description
            "Initial augment file.";
    }

    // augment statements
    grouping ethernet-header-ext-config {
        leaf pcp {
            type uint8 {
                range "0..7";
            }
            description "IEEE 802 Priority Code Point";
        }
        leaf pcp-mask {
            type uint8 {
                range "0..7";
            }
            description "IEEE 802 Priority Code Point";
        }
        leaf dei {
            type uint8 {
                range "0..1";
            }
            description "IEEE 802 Drop Eligible Indicator";
        }
        leaf vlanid {
            type uint16 {
                range "1..4094";
            }
            description "VLAN ID";
        }
    }

    grouping "transport-fields-ext-config" {
        leaf icmp-type {
            type uint8;
            description "ICMP or ICMPv6 Type";
        }
        leaf icmp-code {
            type uint8;
            description "ICMP or ICMPv6 Code";
        }
    }

    augment "/oc-acl:acl/oc-acl:acl-sets/oc-acl:acl-set/oc-acl:acl-entries/oc-acl:acl-entry/oc-acl:l2/oc-acl:config" {
        uses ethernet-header-ext-config;
    }

    augment "/oc-acl:acl/oc-acl:acl-sets/oc-acl:acl-set/oc-acl:acl-entries/oc-acl:acl-entry/oc-acl:l2/oc-acl:state" {
        uses ethernet-header-ext-config;
    }
    
    augment "/oc-acl:acl/oc-acl:acl-sets/oc-acl:acl-set/oc-acl:acl-entries/oc-acl:acl-entry/oc-acl:transport/oc-acl:config" {
        uses transport-fields-ext-config;
    }

    augment "/oc-acl:acl/oc-acl:acl-sets/oc-acl:acl-set/oc-acl:acl-entries/oc-acl:acl-entry/oc-acl:transport/oc-acl:state" {
        uses transport-fields-ext-config;
    }

    typedef ip-protocol-type-ext {
        type union {
            type uint8;
            type identityref {
                base oc-pkt-match-types:IP_PROTOCOL;
            }
        }
    }

    deviation /oc-acl:acl/oc-acl:acl-sets/oc-acl:acl-set/oc-acl:acl-entries/oc-acl:acl-entry/oc-acl:ipv4/oc-acl:config/oc-acl:protocol {
        deviate replace {
            type ip-protocol-type-ext;
        }
    }
    deviation /oc-acl:acl/oc-acl:acl-sets/oc-acl:acl-set/oc-acl:acl-entries/oc-acl:acl-entry/oc-acl:ipv4/oc-acl:state/oc-acl:protocol {
        deviate replace {
            type ip-protocol-type-ext;
        }
    }
    deviation /oc-acl:acl/oc-acl:acl-sets/oc-acl:acl-set/oc-acl:acl-entries/oc-acl:acl-entry/oc-acl:ipv6/oc-acl:config/oc-acl:protocol {
        deviate replace {
            type ip-protocol-type-ext;
        }
    }
    deviation /oc-acl:acl/oc-acl:acl-sets/oc-acl:acl-set/oc-acl:acl-entries/oc-acl:acl-entry/oc-acl:ipv6/oc-acl:state/oc-acl:protocol {
        deviate replace {
            type ip-protocol-type-ext;
        }
    }
	deviation /oc-acl:acl/oc-acl:acl-sets/oc-acl:acl-set/oc-acl:acl-entries/oc-acl:acl-entry/oc-acl:ipv4/oc-acl:config/oc-acl:hop-limit {
		deviate not-supported;
	}
	deviation /oc-acl:acl/oc-acl:acl-sets/oc-acl:acl-set/oc-acl:acl-entries/oc-acl:acl-entry/oc-acl:ipv4/oc-acl:state/oc-acl:hop-limit {
		deviate not-supported;
	}
	deviation /oc-acl:acl/oc-acl:acl-sets/oc-acl:acl-set/oc-acl:acl-entries/oc-acl:acl-entry/oc-acl:ipv6/oc-acl:config/oc-acl:source-flow-label {
		deviate not-supported;
	}
	deviation /oc-acl:acl/oc-acl:acl-sets/oc-acl:acl-set/oc-acl:acl-entries/oc-acl:acl-entry/oc-acl:ipv6/oc-acl:config/oc-acl:destination-flow-label {
		deviate not-supported;
	}
	deviation /oc-acl:acl/oc-acl:acl-sets/oc-acl:acl-set/oc-acl:acl-entries/oc-acl:acl-entry/oc-acl:ipv6/oc-acl:config/oc-acl:hop-limit {
		deviate not-supported;
	}
	deviation /oc-acl:acl/oc-acl:acl-sets/oc-acl:acl-set/oc-acl:acl-entries/oc-acl:acl-entry/oc-acl:ipv6/oc-acl:state/oc-acl:source-flow-label {
		deviate not-supported;
	}
	deviation /oc-acl:acl/oc-acl:acl-sets/oc-acl:acl-set/oc-acl:acl-entries/oc-acl:acl-entry/oc-acl:ipv6/oc-acl:state/oc-acl:destination-flow-label {
		deviate not-supported;
	}
	deviation /oc-acl:acl/oc-acl:acl-sets/oc-acl:acl-set/oc-acl:acl-entries/oc-acl:acl-entry/oc-acl:ipv6/oc-acl:state/oc-acl:hop-limit {
		deviate not-supported;
	}
	deviation /oc-acl:acl/oc-acl:acl-sets/oc-acl:acl-set/oc-acl:acl-entries/oc-acl:acl-entry/oc-acl:input-interface {
		deviate not-supported;
	}
	deviation /oc-acl:acl/oc-acl:acl-sets/oc-acl:acl-set/oc-acl:acl-entries/oc-acl:acl-entry/oc-acl:actions/oc-acl:config/oc-acl:log-action {
		deviate not-supported;
	}
	deviation /oc-acl:acl/oc-acl:acl-sets/oc-acl:acl-set/oc-acl:acl-entries/oc-acl:acl-entry/oc-acl:actions/oc-acl:state/oc-acl:log-action {
		deviate not-supported;
	}
}
