module openconfig-tests {
	namespace "http://github.com/Azure/openconfig-tests";
	prefix oc-test;

	organization
		"SONiC";

	contact
		"SONiC";

	description
		"SONIC TEST Module for Transformer/common-app use";

	revision 2019-10-16 {
		description
			"Initial revision.";
	}


	container openconfig-tests {

		container TABLE_A {

			list TABLE_A_LIST {
				key "id";

                                leaf id {
					type uint32;
				}

				leaf ifname {
					type string {
						pattern "Ethernet([1-3][0-9]{3}|[1-9][0-9]{2}|[1-9][0-9]|[0-9])" {
							error-message "Invalid interface name";
							error-app-tag interface-name-invalid;
						}
					}
				}

				leaf index {
					type uint32;
				}

				leaf-list indices {
					type uint32;
				}

				leaf speed {
					type uint64;
				}

				leaf valid_speeds {
					type string;
				}

				leaf alias {
					type string;
				}

				leaf description {
					type string;
				}

				leaf mtu{
					type uint32 {
						range "1312..9216" {
							error-message "Invalid MTU value";
							error-app-tag mtu-invalid;
						}
					}
				}

				leaf lanes {
					type string;
				}

				leaf admin_status {
					type uint16;
				}
			}
		}
	}
	
}
