module cascade-delete-annot {

    yang-version "1";
    namespace "http://openconfig.net/yang/annotation/cascade-delete-annot";

    prefix "cas-del-annot";

    import cascade-delete { prefix cas-del; }
    import sonic-extensions { prefix sonic-ext; }

    deviation /cas-del:fp-ports {
        deviate add {
            sonic-ext:table-name "PORT";
            sonic-ext:subtree-transformer "fp_ports_sbt_xfmr";
        }
    }
}
